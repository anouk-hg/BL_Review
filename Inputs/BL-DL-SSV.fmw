FME workspace BL-DL-SSV.fmw

Parameters:
- SourceDataset_POSTGIS = Unifiber - AH   # Connection
- DMP_Area_Area_ID = UF013-01   # DMP AREA AREA ID
- Area_ID = 8

Readers:
- POSTGIS_1: POSTGIS from $(SourceDataset_POSTGIS)

MONDAY_ITEM_VIEW_GEOM (reader POSTGIS_1)
    attributes: item_id int8, task text, Doubles text, DMP AREA AREA ID text, DMP AREA NAME text, DMP POSTAL CODE text, DMP MUNICIPALITY text, DMP CITY text, DMP STREET text, DMP HOUSENUMBER text, DMP BUILDING KEY text, DMP BELMAP LU COUNT text, DMP POP AREA NAME text, DMP IN SCOPE text, APP SSV BLDG GRP INDIV TREATMENT text, APP SSV BLDG GRP MAIN ADDRESS text, APP SSV BU COUNT text, APP SSV BUILDING GROUP text, APP SSV BUILDING TYPE text, APP SSV DEPLOYMENT TYPE text, APP SSV LOW FLOOR text, APP SSV LU COUNT text, APP SSV QUADRANT text, APP SSV SU COUNT text, APP SSV TOTAL UNITS text, APP SSV UPPER FLOOR text, SSV ACTUAL DATE text, SSV COMPANY text, SSV AGENT text, SSV BLOCK text,
      SSV DOC LINK text, SSV PLANNED DATE text, SSV REGISTRATION STATUS text, SSV STATUS text, SSV SYNDIC text, SSV SYNDIC MAIL text, SSV SYNDIC NAME text, SSV SYNDIC PHONE text, SSV TIMESTAMP text, TSA 1ST REMINDER DATE text, TSA 2ND REMINDER DATE text, TSA 3RD REMINDER DATE text, TSA 4TH REMINDER DATE text, TSA DOC FOR SIGNATURE text, TSA DOC SIGNED text, TSA COMPANY text, TSA GENERAL ASSEMBLY DATE text, TSA NEGOTIATOR text, TSA NEGOTIATOR COMMENTS text, TSA READY TO SEND DATE text, TSA REFUSED DATE text, TSA REGISTRATION STATUS text, TSA SENT DATE text, TSA SIGNED DATE text, TSA STATUS text, ACT HP CY text, ACT HP CY DEADLINE text, ACT SSV CY text, ACT SSV DEADLINE text, ACT UNIFIBER text,
      ACT UNIFIBER DATE text, APP CCP SSV SU COUNT text, APP CHK SU COUNT text, APP PROCESSED text, BLD ALL READY STATUS text, BLD COMPANY text, BLD FIBER BLOWN ACTUAL DATE text, BLD FIBER BLOWN PLANNED DATE text, BLD FIBER BLOWN STATUS text, BLD FIBER SPLICED ACTUAL DATE text, BLD FIBER SPLICED PLANNED DATE text, BLD FIBER SPLICED STATUS text, BLD INTRO ACTUAL DATE text, BLD INTRO PLANNED DATE text, BLD INTRO STATUS text, BLD SSV USABILITY text, BLD VC ACTUAL DATE text, BLD VC PLANNED DATE text, BLD VC STATUS text, CCP CHECK DONE text, CCP SSV BU COUNT text, CCP SSV LOW FLOOR text, CCP SSV LU COUNT text, CCP SSV QUADRANT text, CCP SSV TOTAL UNITS text, CCP SSV UPPER FLOOR text, CHK SSV BU COUNT text, CHK SSV DOC LINK text, CHK SSV LU COUNT text, CHK SSV QUADRANT text,
      CHK SSV TOTAL UNITS text, CHK SSV UPPER FLOOR text, CHK TSA DOC FOR SIGNATURE text, CHK TSA DOC SIGNED text, CHK TSA STATUS text, PST CENTRAL POP STATUS text, PST DEL STAT CODE DESC text, PST DEL HCA text, PST HP ACTUAL DATE text, PST HP PLANNED DATE text, SSV VALIDATOR text, STS ACTUAL DATE text, STS DOC LINK text, STS PARTNER text, STS PLANNED DATE text, STS QUADRANT text, STS STATUS text, STS UNITS COUNT text, CCP cleanup scope text, CCP CLEANUP COMMENT text, Audit report text, Audit report date text, PRIORITY text, SSV VALIDATION STATUS text, VALIDATION COMMENT SSV text, SSV validation date text, SSV validation counter text, Picture Quality text, Cable/material trajectory text, Quadrant Design text,
      Contact Details text, Building Group Check text, SSV BLDG GRP MAIN ADDRESS CHK text, DMP LOCATION CHK text, SSV SU COUNT CHK text, SSV BU COUNT CHK text, SSV LU COUNT CHK text, SSV TOTAL UNITS CHK text, TSA VALIDATION STATUS text, VALIDATION COMMENT TSA text, TSA validation date text, TSA validation counter text, REWORK STATUS SSV text, REWORK STATUS TSA text, REFUSAL RESPONSIBILITY SSV text, REFUSAL RESPONSIBILITY TSA text, REFUSAL REASON SSV text, REFUSAL REASON TSA text, ACTION REQUIRED FROM SSV text, ACTION REQUIRED FROM TSA text
    -> TestFilter_13
TestFilter_13
    DEFAULT_VALUE = <UNFILTERED>
    PASSED_TEST_GROUP_OUTPUT = FIRST
    TEST_LIST:
      "BOOL_OP,OR,COMPOSITE_TEST,""""""1 OR 2"""""",TEST_CLAUSE,CASE_INSENSITIVE_TEST @Value(VALIDATION COMMENT SSV) CONTAINS uplicat
      CASE_INSENSITIVE_TEST @Value(VALIDATION COMMENT SSV) CONTAINS oublo",@Value(VALIDATION COMMENT SSV) CONTAINS uplicat
    <UNFILTERED> -> AttributeManager
address (reader POSTGIS_1)
    attributes: id serial,BTREE, area_id int4,BTREE, surveyed_by_id int4,BTREE, created_at timestamp, updated_at timestamp, jvid int4,BTREE, jvid_use varchar(255), belmap_address_id int4,BTREE, belmap_building_id int4,BTREE, street_name text,BTREE, house_number text,BTREE, house_number_extension text,BTREE, bus_number text,BTREE, appartment_number text, postal_code text,BTREE, municipality text, building_type varchar(255),BTREE, city text,BTREE, x float8, y float8, home_released bool, home_released_date timestamp, survey_status varchar(255), survey_date timestamp, status varchar(255),BTREE, service_type text, address_source varchar(255),BTREE, delivery_status int4, reason_not_homes_passed int4, dwelling_unit_type varchar(255),
      building_use text, lot text, distribution_point_number text, dependency_of_others int4, homes_passed_plan_date timestamp, homes_passed_actual_date timestamp, civil_plan_date timestamp, installation_type varchar(255), length_estimate_from_street int4, existing_duct_frontyard text, lat float8, lon float8, amount_of_meters_dug int4, cocon_frame text, quadrant text, deleted_at timestamp, street_survey_distribution_way varchar(255), homes_connect_at timestamp, internal_remarks text, action_needed bool, capakey text, nis5 int4, nis9 text, preferred_distribution text, hc_type text, hc_length int4, num_floor int4, area_pop_id int4,BTREE, central_pop_id int4,BTREE, scopelist_v0 date,
      scopelist_v15 date, scopelist_v2 date, first_hp_wip date, first_hp_hca date, sub_address_of int4,BTREE, belmap_version int4,BTREE, home_release_blocked_at timestamp, home_release_blocked_reason varchar(255), main_address bool, fiberzone text, house_entry_deploy_type varchar(255), approved_for_release bool, home_release_reverted_at timestamp, quadrant_pst text, out_of_scope_at timestamp, ftu_location text, mdu_ssv text, quote_approved bool, pst_update_blocked bool, home_release_blocked_by_delay_id int4,BTREE, batch text, building_group text, type text, distance_source text, pst_update_blocked_reason text, amount_of_meters_aerial int4, amount_of_meters_facade int4, homes_passed_wip_actual_date timestamp, ftu_floor int4, ftu_location_other text,
      ftu_other_room bool, excavation_above int4, quote_reference text, quote_required text, asphalt bool, twin_jvid int4, sdu_exceptional bool, meters_public int8, meters_private int8, meters_indoor int8, meters_existing_drop int8, quote_cost int8, rsn_trench text
    -> FeatureJoiner [LEFT]
    -> TestFilter_4
    -> FeatureJoiner_10 [RIGHT]
    -> FeatureJoiner_11 [RIGHT]
Junction_7
    -> With_Twin
    -> FeatureWriter [Output02]
    -> FeatureWriter_2 [Output02]
Junction_9
    -> SDU
    -> FeatureWriter [Output03]
    -> FeatureWriter_2 [Output03]
DuplicateFilter_3
    INPUT_ORDERED_CHOICE_LOOKUP = NO
    KEYATTR = jvid
    INPUT_ORDERED_CHOICE = No
    UNIQUE -> Junction
Junction
    -> BL
    -> DL
    -> TestFilter_2
Note: PST / SSV / Quadrant / Deployement / Action / Condition / 1 / Many / A, Ax, C, Cx, Dx / To build team / 1 / 1 / <= 4 / D / Deployment List / Multiple de 4 (1 donc inférieur à 4, si 5 inférieur à 8), else To build team / 2a,2b / 1 / Many / M, P / To build team / 3 / Many / Many / A, Ax, C, Cx / 7*** / Deployment List / tant que max (min 1LU ou max 20%) / 4a, 4b / Many / Many / A, Ax, C, Cx / 8*** / Deployment List / 5 / Many / Many / A, Ax, C, Cx / 9*** / Deployment List / tant que max (min 1LU ou max 20%) / 6a,6b / Many / Many / Dx, D / Deployment List / Multiple de 4 (1 donc inférieur à 4, si 5 inférieur à 8), else To build team / 7a,7b
SSV_compared_to_DL: TestFilter
    DEFAULT_VALUE = <UNFILTERED>
    PASSED_TEST_GROUP_OUTPUT = FIRST
    TEST_LIST = "BOOL_OP,OR,COMPOSITE_TEST,""""""1"""""",TEST_CLAUSE,TEST @sum(@Value(APP SSV LU COUNT),@Value(APP SSV BU COUNT)) < @Value(Count_DL)",SSV < DMP,"BOOL_OP,OR,COMPOSITE_TEST,""""""1"""""",TEST_CLAUSE,TEST @sum(@Value(APP SSV LU COUNT),@Value(APP SSV BU COUNT)) = @Value(Count_DL)",SSV = DMP,"BOOL_OP,OR,COMPOSITE_TEST,""""""1"""""",TEST_CLAUSE,TEST @sum(@Value(APP SSV LU COUNT),@Value(APP SSV BU COUNT)) > @Value(Count_DL)",SSV > DMP
TestFilter_6
    DEFAULT_VALUE = <UNFILTERED>
    PASSED_TEST_GROUP_OUTPUT = FIRST
    TEST_LIST = "BOOL_OP,OR,COMPOSITE_TEST,""""""1"""""",TEST_CLAUSE,TEST @sum(@Value(APP SSV LU COUNT),@Value(APP SSV BU COUNT)) < @Value(Count_DL)",SSV < DMP,"BOOL_OP,OR,COMPOSITE_TEST,""""""1"""""",TEST_CLAUSE,TEST @sum(@Value(APP SSV LU COUNT),@Value(APP SSV BU COUNT)) = @Value(Count_DL)",SSV = DMP,"BOOL_OP,OR,COMPOSITE_TEST,""""""1"""""",TEST_CLAUSE,TEST @sum(@Value(APP SSV LU COUNT),@Value(APP SSV BU COUNT)) > @Value(Count_DL)",SSV > DMP
    SSV < DMP -> AttributeManager_8
AttributeManager_8
    ATTR_TABLE:
      REMOVE DMP AREA AREA ID (buffer)
      REMOVE DMP AREA NAME (buffer)
      REMOVE DMP POSTAL CODE (buffer)
      REMOVE DMP MUNICIPALITY (buffer)
      REMOVE DMP CITY (buffer)
      REMOVE DMP STREET (buffer)
      REMOVE DMP BELMAP LU COUNT (buffer)
      REMOVE DMP POP AREA NAME (buffer)
      REMOVE DMP IN SCOPE (buffer)
      REMOVE APP SSV BLDG GRP INDIV TREATMENT (buffer)
      REMOVE APP SSV BLDG GRP MAIN ADDRESS (buffer)
      REMOVE APP SSV BUILDING GROUP (buffer)
      REMOVE APP SSV BUILDING TYPE (buffer)
      REMOVE APP SSV DEPLOYMENT TYPE (buffer)
      REMOVE APP SSV LOW FLOOR (buffer)
      REMOVE APP SSV SU COUNT (buffer)
      REMOVE APP SSV UPPER FLOOR (buffer)
      REMOVE house_number_extension (buffer)
      SET_TO Excessive LU - BU (real64) = @Evaluate(@sub(@Value(Count_BL),@sum(@Value(APP SSV LU COUNT),@Value(APP SSV BU COUNT))))
      SET_TO Excessive LU - DL (real64) = @Evaluate(@sub(@Value(Count_BL),@sum(@Value(APP SSV LU COUNT),@Value(APP SSV BU COUNT))))
    -> AttributeCreator_8
    -> FeatureWriter [Output]
    -> FeatureWriter_2 [Output]
AttributeCreator_8
    ATTR_TABLE = SET_TO BL_Review (varchar(9)) = Excessive
    -> Excessive_LU
    -> FeatureWriter_3 [Output]
    -> PythonCaller
AttributeManager_7
    ATTR_TABLE:
      REMOVE DMP AREA AREA ID (buffer)
      REMOVE DMP AREA NAME (buffer)
      REMOVE DMP POSTAL CODE (buffer)
      REMOVE DMP MUNICIPALITY (buffer)
      REMOVE DMP CITY (buffer)
      REMOVE DMP STREET (buffer)
      REMOVE DMP BELMAP LU COUNT (buffer)
      REMOVE DMP POP AREA NAME (buffer)
      REMOVE DMP IN SCOPE (buffer)
      REMOVE APP SSV BLDG GRP INDIV TREATMENT (buffer)
      REMOVE APP SSV BLDG GRP MAIN ADDRESS (buffer)
      REMOVE APP SSV BUILDING GROUP (buffer)
      REMOVE APP SSV BUILDING TYPE (buffer)
      REMOVE APP SSV DEPLOYMENT TYPE (buffer)
      REMOVE APP SSV LOW FLOOR (buffer)
      REMOVE APP SSV SU COUNT (buffer)
      REMOVE APP SSV UPPER FLOOR (buffer)
      REMOVE house_number_extension (buffer)
      SET_TO Potential LU - BL (real64) = @Evaluate(@sub(@sum(@Value(APP SSV LU COUNT),@Value(APP SSV BU COUNT)),@Value(Count_BL)))
      SET_TO Potential LU - DL (real64) = @Evaluate(@sub(@sum(@Value(APP SSV LU COUNT),@Value(APP SSV BU COUNT)),@Value(Count_DL)))
    -> FeatureJoiner_9 [RIGHT]
FeatureJoiner_9
    ATTR_CONFLICT_RES_LOOKUP = USE_LEFT
    GEOMETRY_HANDLING_LOOKUP = USE_RIGHT
    JOIN_KEYS = street_name street_name AUTO house_number_extension DMP HOUSENUMBER AUTO postal_code postal_code AUTO
    JOIN_MODE = Inner
    ATTR_CONFLICT_RES = Prefer Left
    GEOMETRY_HANDLING = Prefer Right
    JOINED -> AttributeCreator_3
    UNJOINED_RIGHT -> AttributeCreator_3
AttributeCreator_3
    ATTR_TABLE = SET_TO Type (varchar(200)) = FME_CONDITIONAL:DEFAULT_VALUE'_FME_NO_OP_'BOOL_OP;OR;COMPOSITE_TEST;1;TEST DMP_delivery_status ATTRIBUTE_IS_MISSING _FME_BLANK_STRING_'New MDU'BOOL_OP;COMPOSITE;COMPOSITE_TEST;( 1 OR 2 OR 3 OR 4 OR 5 ) AND ( 6 );TEST @Value(APP SSV QUADRANT) = A;TEST @Value(APP SSV QUADRANT) = Ax;TEST @Value(APP SSV QUADRANT) = C;TEST @Value(APP SSV QUADRANT) = Cx;TEST @Value(APP SSV QUADRANT) = Dx;TEST @Value(Count_BL) = 1'SDU to MDU in Q Dx,C,Cx,A,Ax'BOOL_OP;COMPOSITE;COMPOSITE_TEST;1 AND 2 AND 3;TEST @Value(APP SSV QUADRANT) = D;TEST @Value(Count_BL) = 1;TEST @Value(APP SSV TOTAL UNITS) <= 4'SDU to MDU in QD - Spare'BOOL_OP;COMPOSITE;COMPOSITE_TEST;1 AND 2 AND 3;TEST @Value(APP SSV QUADRANT) = D;TEST @Value(Count_BL) = 1;TEST @Value(APP SSV TOTAL UNITS) > 4'SDU to MDU in QD - no Spare'BOOL_OP;COMPOSITE;COMPOSITE_TEST;1 OR 2 AND ( 3 );TEST @Value(APP SSV QUADRANT) = M;TEST @Value(APP SSV QUADRANT) = P;TEST @Value(Count_BL) = 1'QM and QP'BOOL_OP;COMPOSITE;COMPOSITE_TEST;( 1 OR 2 OR 3 OR 4 ) AND 5 AND 6 AND 7;TEST @Value(APP SSV QUADRANT) = A;TEST @Value(APP SSV QUADRANT) = Ax;TEST @Value(APP SSV QUADRANT) = C;TEST @Value(APP SSV QUADRANT) = Cx;TEST @Value(Count_BL) > 1;TEST @Left(@Value(DMP_delivery_status),1) = 7;TEST @Evaluate(@sub(@Value(APP SSV TOTAL UNITS),@Value(Count_BL))) <= @max(1,@mult(0.2,@Value(Count_BL)))'Q C,Cx,A,Ax - UG Distribution -  spare'BOOL_OP;COMPOSITE;COMPOSITE_TEST;( 1 OR 2 OR 3 OR 4 ) AND 5 AND 6 AND 7;TEST @Value(APP SSV QUADRANT) = A;TEST @Value(APP SSV QUADRANT) = Ax;TEST @Value(APP SSV QUADRANT) = C;TEST @Value(APP SSV QUADRANT) = Cx;TEST @Value(Count_BL) > 1;TEST @Left(@Value(DMP_delivery_status),1) = 7;TEST @Evaluate(@sub(@Value(APP SSV TOTAL UNITS),@Value(Count_BL))) > @max(1,@mult(0.2,@Value(Count_BL)))'Q C,Cx,A,Ax - UG Distribution - no spare'BOOL_OP;COMPOSITE;COMPOSITE_TEST;( 1 OR 2 OR 3 OR 4 ) AND 5 AND 6;TEST @Value(APP SSV QUADRANT) = A;TEST @Value(APP SSV QUADRANT) = Ax;TEST @Value(APP SSV QUADRANT) = C;TEST @Value(APP SSV QUADRANT) = Cx;TEST @Value(Count_BL) > 1;TEST @Left(@Value(DMP_delivery_status),1) = 8'Q C,Cx,A,Ax - Facade Distribution 'BOOL_OP;COMPOSITE;COMPOSITE_TEST;( 1 OR 2 OR 3 OR 4 ) AND 5 AND 6 AND 7;TEST @Value(APP SSV QUADRANT) = A;TEST @Value(APP SSV QUADRANT) = Ax;TEST @Value(APP SSV QUADRANT) = C;TEST @Value(APP SSV QUADRANT) = Cx;TEST @Value(Count_BL) > 1;TEST @Left(@Value(DMP_delivery_status),1) = 9;TEST @Evaluate(@sub(@Value(APP SSV TOTAL UNITS),@Value(Count_BL))) <= @max(1,@mult(0.2,@Value(Count_BL)))'Q C,Cx,A,Ax - Aerial Distribution - Spare'BOOL_OP;COMPOSITE;COMPOSITE_TEST;( 1 OR 2 OR 3 OR 4 ) AND 5 AND 6 AND 7;TEST @Value(APP SSV QUADRANT) = A;TEST @Value(APP SSV QUADRANT) = Ax;TEST @Value(APP SSV QUADRANT) = C;TEST @Value(APP SSV QUADRANT) = Cx;TEST @Value(Count_BL) > 1;TEST @Left(@Value(DMP_delivery_status),1) = 9;TEST @Evaluate(@sub(@Value(APP SSV TOTAL UNITS),@Value(Count_BL))) > @max(1,@mult(0.2,@Value(Count_BL)))'Q C,Cx,A,Ax - Aerial Distribution - no Spare'BOOL_OP;COMPOSITE;COMPOSITE_TEST;( 1 OR 2 ) AND 3 AND 4;TEST @Value(APP SSV QUADRANT) = D;TEST @Value(APP SSV QUADRANT) = Dx;TEST @Value(Count_BL) > 1;TEST @Value(APP SSV TOTAL UNITS) <= @mult(@add(@round(@div(@Value(Count_BL),4),0),1),4)'Q D,Dx - Spare'BOOL_OP;COMPOSITE;COMPOSITE_TEST;( 1 OR 2 ) AND 3 AND 4;TEST @Value(APP SSV QUADRANT) = D;TEST @Value(APP SSV QUADRANT) = Dx;TEST @Value(Count_BL) > 1;TEST @Value(APP SSV TOTAL UNITS) > @mult(@add(@round(@div(@Value(Count_BL),4),0),1),4)'Q D,Dx - no Spare'BOOL_OP;OR;COMPOSITE_TEST;1;TEST APP SSV QUADRANT NOT_ATTRIBUTE_HAS_A_VALUE _FME_BLANK_STRING_'No SSV'FME_NUM_CONDITIONS14___
    -> Quadrant_via_SSV_2
Quadrant_via_SSV_2: TestFilter
    DEFAULT_VALUE = <UNFILTERED>
    PASSED_TEST_GROUP_OUTPUT = FIRST
    TEST_LIST:
      "BOOL_OP,OR,COMPOSITE_TEST,""""""1"""""",TEST_CLAUSE,TEST DMP_delivery_status ATTRIBUTE_IS_MISSING """,New MDU,"BOOL_OP,COMPOSITE,COMPOSITE_TEST,""""""( 1 OR 2 OR 3 OR 4 OR 5 ) AND ( 6 )"""""",TEST_CLAUSE,TEST @Value(APP SSV QUADRANT) = A
      TEST @Value(APP SSV QUADRANT) = Ax
      TEST @Value(APP SSV QUADRANT) = C
      TEST @Value(APP SSV QUADRANT) = Cx
      TEST @Value(APP SSV QUADRANT) = Dx
      TEST @Value(Count_BL) = 1",Case 1,"BOOL_OP,AND,COMPOSITE_TEST,""""""1 AND 2 AND 3"""""",TEST_CLAUSE,TEST @Value(APP SSV QUADRANT) = D
      TEST @Value(Count_BL) = 1
      TEST @Value(APP SSV TOTAL UNITS) <= 4",Case 2a,"BOOL_OP,AND,COMPOSITE_TEST,""""""1 AND 2 AND 3"""""",TEST_CLAUSE,TEST @Value(APP SSV QUADRANT) = D
      TEST @Value(Count_BL) = 1
      TEST @Value(APP SSV TOTAL UNITS) > 4",Case 2b,"BOOL_OP,COMPOSITE,COMPOSITE_TEST,""""""1 OR 2 AND ( 3 )"""""",TEST_CLAUSE,TEST @Value(APP SSV QUADRANT) = M
      TEST @Value(APP SSV QUADRANT) = P
      TEST @Value(Count_BL) = 1",Case 3,"BOOL_OP,COMPOSITE,COMPOSITE_TEST,""""""( 1 OR 2 OR 3 OR 4 ) AND 5 AND 6 AND 7"""""",TEST_CLAUSE,TEST @Value(APP SSV QUADRANT) = A
      TEST @Value(APP SSV QUADRANT) = Ax
      TEST @Value(APP SSV QUADRANT) = C
      TEST @Value(APP SSV QUADRANT) = Cx
      TEST @Value(Count_BL) > 1
      TEST @Left(@Value(DMP_delivery_status),1) = 7
      TEST @Evaluate(@sub(@Value(APP SSV TOTAL UNITS),@Value(Count_BL))) <= @max(1,@mult(0.2,@Value(Count_BL)))",Case 4a,"BOOL_OP,COMPOSITE,COMPOSITE_TEST,""""""( 1 OR 2 OR 3 OR 4 ) AND 5 AND 6 AND 7"""""",TEST_CLAUSE,TEST @Value(APP SSV QUADRANT) = A
      TEST @Value(APP SSV QUADRANT) = Ax
      TEST @Value(APP SSV QUADRANT) = C
      TEST @Value(APP SSV QUADRANT) = Cx
      TEST @Value(Count_BL) > 1
      TEST @Left(@Value(DMP_delivery_status),1) = 7
      TEST @Evaluate(@sub(@Value(APP SSV TOTAL UNITS),@Value(Count_BL))) > @max(1,@mult(0.2,@Value(Count_BL)))",Case 4b,"BOOL_OP,COMPOSITE,COMPOSITE_TEST,""""""( 1 OR 2 OR 3 OR 4 ) AND 5 AND 6"""""",TEST_CLAUSE,TEST @Value(APP SSV QUADRANT) = A
      TEST @Value(APP SSV QUADRANT) = Ax
      TEST @Value(APP SSV QUADRANT) = C
      TEST @Value(APP SSV QUADRANT) = Cx
      TEST @Value(Count_BL) > 1
      TEST @Left(@Value(DMP_delivery_status),1) = 8",Case 5,"BOOL_OP,COMPOSITE,COMPOSITE_TEST,""""""( 1 OR 2 OR 3 OR 4 ) AND 5 AND 6 AND 7"""""",TEST_CLAUSE,TEST @Value(APP SSV QUADRANT) = A
      TEST @Value(APP SSV QUADRANT) = Ax
      TEST @Value(APP SSV QUADRANT) = C
      TEST @Value(APP SSV QUADRANT) = Cx
      TEST @Value(Count_BL) > 1
      TEST @Left(@Value(DMP_delivery_status),1) = 9
      TEST @Evaluate(@sub(@Value(APP SSV TOTAL UNITS),@Value(Count_BL))) <= @max(1,@mult(0.2,@Value(Count_BL)))",Case 6a,"BOOL_OP,COMPOSITE,COMPOSITE_TEST,""""""( 1 OR 2 OR 3 OR 4 ) AND 5 AND 6 AND 7"""""",TEST_CLAUSE,TEST @Value(APP SSV QUADRANT) = A
      TEST @Value(APP SSV QUADRANT) = Ax
      TEST @Value(APP SSV QUADRANT) = C
      TEST @Value(APP SSV QUADRANT) = Cx
      TEST @Value(Count_BL) > 1
      TEST @Left(@Value(DMP_delivery_status),1) = 9
      TEST @Evaluate(@sub(@Value(APP SSV TOTAL UNITS),@Value(Count_BL))) > @max(1,@mult(0.2,@Value(Count_BL)))",Case 6b,"BOOL_OP,COMPOSITE,COMPOSITE_TEST,""""""( 1 OR 2 ) AND 3 AND 4"""""",TEST_CLAUSE,TEST @Value(APP SSV QUADRANT) = D
      TEST @Value(APP SSV QUADRANT) = Dx
      TEST @Value(Count_BL) > 1
      TEST @Value(APP SSV TOTAL UNITS) <= @mult(@add(@round(@div(@Value(Count_BL),4),0),1),4)",Case 7a,"BOOL_OP,COMPOSITE,COMPOSITE_TEST,""""""( 1 OR 2 ) AND 3 AND 4"""""",TEST_CLAUSE,TEST @Value(APP SSV QUADRANT) = D
      TEST @Value(APP SSV QUADRANT) = Dx
      TEST @Value(Count_BL) > 1
      TEST @Value(APP SSV TOTAL UNITS) > @mult(@add(@round(@div(@Value(Count_BL),4),0),1),4)",Case 7b,"BOOL_OP,OR,COMPOSITE_TEST,""""""1"""""",TEST_CLAUSE,TEST APP SSV QUADRANT NOT_ATTRIBUTE_HAS_A_VALUE """,No SSV
    New MDU -> Junction_5
    Case 1 -> Junction_5
    Case 2a -> Junction_6
    Case 2b -> Junction_5
    Case 3 -> Junction_5
    Case 4a -> Junction_6
    Case 4b -> Junction_5
    Case 5 -> Junction_6
    Case 6a -> Junction_6
    Case 6b -> Junction_5
    Case 7a -> Junction_6
    Case 7b -> Junction_5
    No SSV -> Junction_5
    <UNFILTERED> -> Junction_5
Junction_5
    -> AttributeCreator_6
    -> FeatureWriter [Output00]
    -> FeatureWriter_2 [Output00]
AttributeCreator_6
    ATTR_TABLE = SET_TO BL_Review (varchar(6)) = Review
    -> LU_to_review
    -> FeatureWriter_3 [Output00]
    -> PythonCaller
FeatureWriter_3 [off]
    DATASET = $(FME_MF_DIR_ENCODED)Outputs\Test.xlsx
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert
Junction_6
    -> AttributeCreator_7
    -> FeatureWriter [Output01]
    -> FeatureWriter_2 [Output01]
AttributeCreator_7
    ATTR_TABLE = SET_TO BL_Review (varchar(9)) = Add to DL
    -> LU_to_DL
    -> PythonCaller
PythonCaller
    HIDE_ATTRIBUTES = "APP SSV QUADRANT" "APP SSV TOTAL UNITS" belmap_building_id Count_BL "DMP LOCATION CHK" DMP_delivery_status house_number_extension postal_code "Potential LU - BL" "Potential LU - DL" task Type
    NEW_ATTRIBUTES = action varchar(200) feedback varchar(200) bl_review varchar(200) bus_number varchar(200) jvid varchar(200) status varchar(200) delivery_status varchar(200) DMP BUIDLING KEY varchar(200) DMP HOUSENUMBER varchar(200)
    PYTHONSOURCE:
      """
      LU Reconciliation — FME 2024.2 PythonCaller
      Reconciles Logement Unit counts between Deployment List (DL) and Build List (BL)
      for Belgian fiber deployment.

      Class: FeatureProcessor
      Methods: __init__, input(feature), close()
      """

      import re
      from collections import Counter

      import fmeobjects


      # ---------------------------------------------------------------------------
      # Helpers
      # ---------------------------------------------------------------------------

      def _parse_csv(value):
          """Return a list of stripped strings from a comma-separated FME attribute.
          Also handles dot-separated floats (jvid edge case like '10083231.10083232').
          """
          if value is None or str(value).strip() == "":
              return []
          s = str(value).strip()
          # Detect dot-separated float pattern (digits.digits, no commas)
          if re.fullmatch(r"[\d.]+", s) and "." in s and "," not in s:
              parts = s.split(".")
              # Strip trailing zeros that look like float artifacts (.0)
              return [p for p in parts if p]
          return [p.strip() for p in s.split(",")]


      def _get_attr(feature, name):
          """Safely retrieve an FME attribute as a Python string (or None)."""
          try:
              v = feature.getAttribute(name)
          except Exception:
              v = None
          if v is None:
              return None
          s = str(v).strip()
          return s if s not in ("", "None") else None


      def _safe_int(val, default=0):
          try:
              return int(float(str(val)))
          except (ValueError, TypeError):
              return default


      # ---------------------------------------------------------------------------
      # Bus-number logic
      # ---------------------------------------------------------------------------

      def _parse_busnum(bn):
          """Return (prefix, digits_str, numeric_int) or None if not parseable."""
          if not bn:
              return None
          bn = bn.strip()
          m = re.fullmatch(r"([A-Za-z]*)(\d+)", bn)
          if m:
              prefix = m.group(1).upper()
              digits = m.group(2)
              return prefix, digits, int(digits)
          return None


      def _sort_key(bn):
          """Logical sort key: (0, prefix, numeric) for standard; (1, ...) else; empty last."""
          if not bn or not bn.strip():
              return (2, "", 0, "")
          parsed = _parse_busnum(bn.strip())
          if parsed:
              prefix, digits, num = parsed
              return (0, prefix, num, "")
          return (1, "", 0, bn.strip().lower())


      def _normalize_busnum(bn):
          """Strip common prefixes and leading zeros for duplicate-normalization."""
          if not bn:
              return ""
          s = bn.strip().lower()
          for pfx in ("bte", "box", "apt", "app", "flat", "unit"):
              if s.startswith(pfx):
                  s = s[len(pfx):]
                  break
          s = s.lstrip("0") or "0"
          return s


      def detect_outliers(bus_numbers):
          """
          Given a list of raw bus_numbers (may include None/""), return a set of
          indices that are outliers.

          Rules:
          1. Non-dominant prefix
          2. Wrong digit length within dominant-prefix group
          3. Duplicate normalization (keep dominant-format one, flag the other)
          """
          outlier_idx = set()

          parsed = [_parse_busnum(bn) if bn and bn.strip() else None
                    for bn in bus_numbers]

          # Safe defaults — used later in Rule 3 even if Rule 1/2 don't fire
          dominant_prefix = ""
          dominant_dl = None

          # --- Rule 1: non-dominant prefix ---
          prefixes = [p[0] for p in parsed if p is not None]
          if prefixes:
              prefix_counts = Counter(prefixes)
              dominant_prefix, dominant_count = prefix_counts.most_common(1)[0]
              if dominant_count > 1:
                  for i, p in enumerate(parsed):
                      if p is not None and p[0] != dominant_prefix:
                          outlier_idx.add(i)

          # --- Rule 2: wrong digit length in dominant-prefix group ---
          # Intent: catch genuine typos like B1200 in a B101-B103 group.
          # Do NOT flag values whose extra/fewer digits are simply the result of
          # natural numeric growth crossing a power-of-10 boundary (e.g. 9 → 10,
          # 99 → 100).  Strategy:
          #   • If the numeric range of the group stays within a single digit-length
          #     band (min and max have the same number of natural digits), apply the
          #     rule strictly: any value with a different padded digit count is an
          #     outlier.
          #   • If the range crosses a boundary (e.g. 8-12 spans 1- and 2-digit
          #     numbers), only flag values whose digit length differs from the strict
          #     majority AND whose difference is ≥ 1 digit — this catches a stray
          #     4-digit value in a mostly-3-digit group while leaving natural
          #     rollovers alone.
          dominant_group_idx = [i for i, p in enumerate(parsed)
                                if p is not None and p[0] == dominant_prefix
                                and i not in outlier_idx]
          if dominant_group_idx:
              nums = [parsed[i][2] for i in dominant_group_idx]
              min_num, max_num = min(nums), max(nums)
              range_spans_boundary = (len(str(min_num)) != len(str(max_num)))

              digit_lengths = [len(parsed[i][1]) for i in dominant_group_idx]
              dl_counts = Counter(digit_lengths)
              dominant_dl, dominant_dl_count = dl_counts.most_common(1)[0]
              total_in_group = len(dominant_group_idx)

              if not range_spans_boundary:
                  # All values sit within the same digit-length band (e.g. 10–99 or
                  # B101–B999).  Any value with a different padded digit count is a
                  # genuine outlier (e.g. B1200 in a B101–B103 group).
                  if dominant_dl_count > 1:
                      for i in dominant_group_idx:
                          if len(parsed[i][1]) != dominant_dl:
                              outlier_idx.add(i)
              # When the range naturally crosses a power-of-10 boundary (e.g. 1–16,
              # 8–12, 98–102) the mixed digit lengths are expected — do not flag
              # anything as a digit-length outlier.

          # --- Rule 3: duplicate normalization ---
          norm_map = {}  # normalized -> first index with dominant format
          for i, bn in enumerate(bus_numbers):
              if i in outlier_idx or not bn or not bn.strip():
                  continue
              norm = _normalize_busnum(bn)
              if norm in norm_map:
                  # Keep dominant-format, flag the other
                  other_i = norm_map[norm]
                  # Choose which to flag: prefer keeping the one matching dominant prefix/length
                  p_i = parsed[i]
                  p_other = parsed[other_i]
                  def is_dominant(p):
                      if p is None:
                          return False
                      ok = (p[0] == dominant_prefix)
                      if dominant_group_idx and dominant_dl is not None:
                          ok = ok and (len(p[1]) == dominant_dl)
                      return ok
                  if is_dominant(p_i) and not is_dominant(p_other):
                      outlier_idx.add(other_i)
                      norm_map[norm] = i
                  else:
                      outlier_idx.add(i)
              else:
                  norm_map[norm] = i

          return outlier_idx


      def suggest_bus_numbers(existing, n_add):
          """
          Suggest n_add new bus_numbers that don't conflict with existing ones.
          Uses floor/unit dimension analysis.
          """
          if n_add <= 0:
              return []

          # Filter to parseable, non-outlier existing values
          existing_clean = [b for b in existing if b and b.strip()]
          outlier_idx = detect_outliers(existing_clean)
          analysis_pool = [b for i, b in enumerate(existing_clean) if i not in outlier_idx]

          parsed_pool = [_parse_busnum(b) for b in analysis_pool]
          parsed_pool = [p for p in parsed_pool if p is not None]

          existing_set = set(b.strip() for b in existing_clean)

          if not parsed_pool:
              # Fallback: plain integers starting from 1
              suggestions = []
              counter = 1
              while len(suggestions) < n_add:
                  candidate = str(counter)
                  if candidate not in existing_set:
                      suggestions.append(candidate)
                  counter += 1
              return suggestions

          # Determine dominant prefix and digit length
          prefixes = [p[0] for p in parsed_pool]
          prefix_counts = Counter(prefixes)
          dominant_prefix = prefix_counts.most_common(1)[0][0]

          dominant_parsed = [p for p in parsed_pool if p[0] == dominant_prefix]
          digit_lengths = [len(p[1]) for p in dominant_parsed]
          dl_counts = Counter(digit_lengths)
          pad_len = dl_counts.most_common(1)[0][0]

          # Pad all digit strings to pad_len
          padded_nums = [p[2] for p in dominant_parsed]  # integer values

          if len(padded_nums) == 1:
              # Only one value — just increment
              suggestions = []
              next_val = padded_nums[0] + 1
              while len(suggestions) < n_add:
                  candidate = dominant_prefix + str(next_val).zfill(pad_len)
                  if candidate not in existing_set:
                      suggestions.append(candidate)
                  next_val += 1
              return suggestions

          # Analyze digit positions
          padded_strs = [str(v).zfill(pad_len) for v in padded_nums]

          # Find varying positions
          pos_values = []
          for pos in range(pad_len):
              vals = set(s[pos] for s in padded_strs)
              pos_values.append(vals)

          varying_positions = [i for i, vals in enumerate(pos_values) if len(vals) > 1]
          fixed_positions = [i for i, vals in enumerate(pos_values) if len(vals) == 1]

          if not varying_positions:
              # All identical — just increment
              suggestions = []
              next_val = max(padded_nums) + 1
              while len(suggestions) < n_add:
                  candidate = dominant_prefix + str(next_val).zfill(pad_len)
                  if candidate not in existing_set:
                      suggestions.append(candidate)
                  next_val += 1
              return suggestions

          # Leftmost varying position = "floor/wing" dimension
          floor_pos = varying_positions[0]
          inner_positions = varying_positions[1:] if len(varying_positions) > 1 else []

          # Get fixed digits
          fixed_digits = {pos: list(pos_values[pos])[0] for pos in fixed_positions}

          # Get current floor values and inner combinations
          floor_vals = sorted(set(int(s[floor_pos]) for s in padded_strs))
          max_floor = max(floor_vals)

          if inner_positions:
              inner_combinations = sorted(set(
                  tuple(s[p] for p in inner_positions) for s in padded_strs
              ))
          else:
              inner_combinations = [()]

          suggestions = []
          next_floor = max_floor + 1

          while len(suggestions) < n_add:
              for combo in inner_combinations:
                  if len(suggestions) >= n_add:
                      break
                  # Build the candidate string
                  chars = ['0'] * pad_len
                  for pos, digit in fixed_digits.items():
                      chars[pos] = digit
                  chars[floor_pos] = str(next_floor)
                  for p, d in zip(inner_positions, combo):
                      chars[p] = d
                  candidate = dominant_prefix + "".join(chars)
                  if candidate not in existing_set:
                      suggestions.append(candidate)
                      existing_set.add(candidate)
              next_floor += 1
              if next_floor > 99:  # Safety valve
                  break

          # If we still need more (edge cases), fall back to plain increment
          if len(suggestions) < n_add:
              max_val = max(padded_nums)
              counter = max_val + 1
              while len(suggestions) < n_add:
                  candidate = dominant_prefix + str(counter).zfill(pad_len)
                  if candidate not in existing_set:
                      suggestions.append(candidate)
                      existing_set.add(candidate)
                  counter += 1

          return suggestions


      # ---------------------------------------------------------------------------
      # Core MDU processor
      # ---------------------------------------------------------------------------

      def process_mdu(mdu):
          """
          Process one MDU dict and return a list of LU dicts (one per output row).

          mdu keys:
              building_key, housenumber, bl_review,
              target (int), count_dl (int),
              jvids (list), bus_numbers (list), statuses (list), delivery_statuses (list)
          """
          building_key = mdu["building_key"]
          housenumber = mdu["housenumber"]
          bl_review = mdu["bl_review"]
          target = mdu["target"]

          jvids = mdu["jvids"]
          bus_numbers = mdu["bus_numbers"]
          statuses = mdu["statuses"]
          delivery_statuses = mdu["delivery_statuses"]

          # Normalise list lengths to the maximum of all lists
          n_lu = max(len(jvids), len(bus_numbers), len(statuses), len(delivery_statuses), 1)

          def pad(lst, length):
              return lst + [""] * (length - len(lst))

          jvids = pad(jvids, n_lu)
          bus_numbers = pad(bus_numbers, n_lu)
          statuses = pad(statuses, n_lu)
          delivery_statuses = pad(delivery_statuses, n_lu)

          # Build LU records
          lus = []
          for i in range(n_lu):
              lus.append({
                  "jvid": jvids[i],
                  "bus_number": bus_numbers[i],
                  "status": statuses[i],
                  "delivery_status": delivery_statuses[i],
                  "action": "KEEP",
                  "feedback": "",
                  "building_key": building_key,
                  "housenumber": housenumber,
                  "bl_review": bl_review,
              })

          # -----------------------------------------------------------------------
          # Pre-existing duplicate warning
          # -----------------------------------------------------------------------
          bn_count = Counter(lu["bus_number"] for lu in lus if lu["bus_number"])
          for lu in lus:
              bn = lu["bus_number"]
              if bn and bn_count[bn] > 1:
                  lu["feedback"] = f"Warning: duplicate bus_number ({bn}) in source data"

          # -----------------------------------------------------------------------
          # Delta
          # -----------------------------------------------------------------------
          n_remove = n_lu - target
          n_add = target - n_lu

          if n_remove == 0 and n_add == 0:
              # All KEEP — feedback already set (or empty)
              return lus

          # -----------------------------------------------------------------------
          # REMOVE logic
          # -----------------------------------------------------------------------
          if n_remove > 0:
              # Step 2a: Lock
              locked = [False] * n_lu

              for i, lu in enumerate(lus):
                  if lu["status"].upper() == "HOMES_CONNECT":
                      locked[i] = True

              if target == 1:
                  # Lock first LU with empty/null bus_number
                  for i, lu in enumerate(lus):
                      if not lu["bus_number"]:
                          locked[i] = True
                          lu["feedback"] = "Kept: NULL bus_number retained (MDU becoming SDU)"
                          break

              unlocked_indices = [i for i in range(n_lu) if not locked[i]]

              # Step 2b: Flag removal candidates
              unlocked_statuses_eq = len(set(lus[i]["delivery_status"] for i in unlocked_indices)) <= 1

              # Track seen bus_numbers for duplicate detection
              seen_bus_numbers = {}  # bus_number -> first unlocked index
              candidate_flags = {i: [] for i in unlocked_indices}

              # Outlier detection on unlocked bus_numbers
              unlocked_bns = [lus[i]["bus_number"] for i in unlocked_indices]
              outlier_idx_set = detect_outliers(unlocked_bns)
              outlier_global = {unlocked_indices[j] for j in outlier_idx_set}

              for i in unlocked_indices:
                  lu = lus[i]
                  ds = lu["delivery_status"]
                  bn = lu["bus_number"]

                  # Delivery-status flags (only when statuses differ)
                  if not unlocked_statuses_eq:
                      if ds and ds.startswith("2"):
                          candidate_flags[i].append("delivery_status starts with 2")
                      if ds and not ds.endswith("5"):
                          candidate_flags[i].append("delivery_status not ending with 5")

                  # Empty bus_number (multiple unlocked LUs)
                  if not bn and len(unlocked_indices) > 1:
                      candidate_flags[i].append("bus_number is empty/null")

                  # Outlier bus_number
                  if i in outlier_global:
                      candidate_flags[i].append(f"bus_number outlier ({bn})")

                  # Duplicate bus_number (second+ occurrence)
                  if bn:
                      if bn in seen_bus_numbers:
                          candidate_flags[i].append(f"duplicate bus_number ({bn})")
                      else:
                          seen_bus_numbers[bn] = i

              # Step 2c: Remove
              candidates = [i for i in unlocked_indices if candidate_flags[i]]
              non_candidates = [i for i in unlocked_indices if not candidate_flags[i]]

              # Sort by bus_number logical order (remove from end first)
              candidates_sorted = sorted(candidates, key=lambda i: _sort_key(lus[i]["bus_number"]))
              non_candidates_sorted = sorted(non_candidates, key=lambda i: _sort_key(lus[i]["bus_number"]))

              to_remove = []
              remaining_remove = n_remove

              # Remove candidates from end first
              while remaining_remove > 0 and candidates_sorted:
                  idx = candidates_sorted.pop()  # from end (largest sort key)
                  to_remove.append(idx)
                  remaining_remove -= 1

              # If still need to remove, take from non-candidates end
              while remaining_remove > 0 and non_candidates_sorted:
                  idx = non_candidates_sorted.pop()
                  to_remove.append(idx)
                  remaining_remove -= 1

              to_remove_set = set(to_remove)

              # Assign actions and feedback
              for i in unlocked_indices:
                  lu = lus[i]
                  if i in to_remove_set:
                      flags = candidate_flags[i]
                      if flags:
                          lu["feedback"] = "Remove: " + ", ".join(flags)
                      else:
                          lu["feedback"] = "Remove: removed from end (no candidate flags)"
                      lu["action"] = "REMOVE"
                  else:
                      flags = candidate_flags[i]
                      if flags:
                          lu["feedback"] = "Kept (candidate but not needed): " + ", ".join(flags)
                      # else: keep existing feedback (duplicate warning) or empty

          # -----------------------------------------------------------------------
          # ADD logic
          # -----------------------------------------------------------------------
          if n_add > 0:
              existing_bns = [lu["bus_number"] for lu in lus]
              suggestions = suggest_bus_numbers(existing_bns, n_add)

              for k in range(n_add):
                  suggested = suggestions[k] if k < len(suggestions) else ""
                  new_lu = {
                      "jvid": "",
                      "bus_number": suggested,
                      "status": "",
                      "delivery_status": "",
                      "action": "ADD",
                      "feedback": f"New LU — suggested bus_number: {suggested}",
                      "building_key": building_key,
                      "housenumber": housenumber,
                      "bl_review": bl_review,
                  }
                  lus.append(new_lu)

          return lus


      # ---------------------------------------------------------------------------
      # FME FeatureProcessor
      # ---------------------------------------------------------------------------

      class FeatureProcessor(object):

          def __init__(self):
              self._mdus = []

          def input(self, feature):
              """Collect incoming MDU features."""

              def ga(name):
                  return _get_attr(feature, name)

              building_key = ga("DMP BUILDING KEY")
              housenumber = ga("DMP HOUSENUMBER")
              bl_review = ga("BL_Review") or ""

              # Target LU count
              ssv_bu = _safe_int(ga("APP SSV BU COUNT"), 0)
              ssv_lu = _safe_int(ga("APP SSV LU COUNT"), 0)
              target = ssv_bu + ssv_lu

              count_dl = _safe_int(ga("Count_DL"), 0)

              # Parse comma/dot-separated lists
              jvids = _parse_csv(ga("jvid"))
              bus_numbers = _parse_csv(ga("bus_number"))
              statuses = _parse_csv(ga("status"))
              delivery_statuses = _parse_csv(ga("delivery_status"))

              self._mdus.append({
                  "building_key": building_key,
                  "housenumber": housenumber,
                  "bl_review": bl_review,
                  "target": target,
                  "count_dl": count_dl,
                  "jvids": jvids,
                  "bus_numbers": bus_numbers,
                  "statuses": statuses,
                  "delivery_statuses": delivery_statuses,
              })

          def close(self):
              """Process all MDUs and emit one FMEFeature per LU."""
              for mdu in self._mdus:
                  lu_rows = process_mdu(mdu)
                  for lu in lu_rows:
                      out = fmeobjects.FMEFeature()
                      out.setAttribute("DMP BUILDING KEY", lu["building_key"] or "")
                      out.setAttribute("DMP HOUSENUMBER", lu["housenumber"] or "")
                      out.setAttribute("jvid", lu["jvid"] or "")
                      out.setAttribute("bus_number", lu["bus_number"] or "")
                      out.setAttribute("status", lu["status"] or "")
                      out.setAttribute("delivery_status", lu["delivery_status"] or "")
                      out.setAttribute("action", lu["action"])
                      out.setAttribute("feedback", lu["feedback"])
                      out.setAttribute("bl_review", lu["bl_review"] or "")
                      self.pyoutput(out)
    PYTHONSYMBOL = FeatureProcessor
    -> FeatureJoiner_12 [LEFT]
Aggregator_4
    ACCUM_ATTRS_NAME = Drop Incoming Attributes
    AGGREGATE_TYPE = Homogeneous Collection (If Possible)
    COUNT_ATTR = BL_v1
    MODE = Geometry - Assemble One Level
    SEP = ,
    AGGREGATE -> AttributeManager_17
AttributeManager_17
    ATTR_TABLE = SET_TO UF id (varchar(200)) = $(DMP_Area_Area_ID)
    -> Junction_12
Note: FeatureJoiner_16 : Left
Junction_12
    -> Junction_13
FeatureJoiner_12
    ATTR_CONFLICT_RES_LOOKUP = USE_LEFT
    GEOMETRY_HANDLING_LOOKUP = USE_LEFT
    JOIN_KEYS = jvid jvid AUTO
    JOIN_MODE = Inner
    ATTR_CONFLICT_RES = Prefer Left
    GEOMETRY_HANDLING = Prefer Left
    JOINED -> TestFilter_5
    UNJOINED_LEFT -> AttributeManager_11
    UNJOINED_RIGHT -> TestFilter_5
AttributeManager_11
    ATTR_TABLE:
      RENAME_SET_VALUE DMP HOUSENUMBER > house_number_extension (buffer)
      RENAME_SET_VALUE DMP BUILDING KEY > belmap_building_id (buffer)
    -> TestFilter_5
TestFilter_5
    DEFAULT_VALUE = <UNFILTERED>
    PASSED_TEST_GROUP_OUTPUT = FIRST
    TEST_LIST = "BOOL_OP,OR,COMPOSITE_TEST,""""""1"""""",TEST_CLAUSE,TEST @Value(action) = REMOVE",@Value(action) = REMOVE
    <UNFILTERED> -> Aggregator_3
Aggregator_3
    ACCUM_ATTRS_NAME = Drop Incoming Attributes
    AGGREGATE_TYPE = Homogeneous Collection (If Possible)
    COUNT_ATTR = BL_v2
    MODE = Geometry - Assemble One Level
    SEP = ,
    AGGREGATE -> AttributeManager_16
AttributeManager_16
    ATTR_TABLE = SET_TO UF id (varchar(200)) = $(DMP_Area_Area_ID)
    -> FeatureJoiner_17 [LEFT]
address_scoping (reader POSTGIS_1)
    attributes: id serial,PrimaryKey, area_id int4, parent_address int4, created_at timestamp, updated_at timestamp, bldg_key int4, addr_key int4,BTREE, source text, axon_name text, laxon_name text, pc text, street_nm text, hnr_base text, hnr_full text, appt_nr text, bus_nr text, x0 float8, y0 float8, lon0 float8, lat0 float8, nis5_code int4, nis9_code text, capakey text, remark text, design_code text, version_id int4, scopelist_v0 date, scopelist_v15 date, scopelist_v2 date, dwelling_unit_type text,
      quadrant text, main_address bool, deleted_at timestamp, last_processed_at timestamp, fiberzone text
    -> TestFilter_10
Junction_3
    -> New_SDU
    -> FeatureWriter [Output04]
    -> FeatureWriter_2 [Output04]
area (reader POSTGIS_1)
    attributes: id serial,PrimaryKey, contractor_id int4,BTREE, created_at timestamp, updated_at timestamp, area_name text,Unique, area_id text, import_id int4, area_released bool, region_name text, homes_passed_contractor_id int4, area_polygon_id int4,Unique, area_released_date timestamp, pst_roll_out_end_date timestamp, monday_board_id text, monday_group_id text, gf_project varchar(255), new_contractor_id int4,BTREE, new_contractor_from timestamp, ssv_contractor_id int4,BTREE
    -> TestFilter_14
TestFilter_14
    DEFAULT_VALUE = <UNFILTERED>
    PASSED_TEST_GROUP_OUTPUT = FIRST
    TEST_LIST = "BOOL_OP,OR,COMPOSITE_TEST,""""""1"""""",TEST_CLAUSE,TEST @Value(area_id) = $(DMP_Area_Area_ID)",@Value(area_id) = __DMP_Area_Area_ID_
    @Value(area_id) = __DMP_Area_Area_ID_ -> AttributeManager_12
AttributeManager_12
    ATTR_TABLE:
      REMOVE contractor_id (int32)
      REMOVE created_at (datetime)
      REMOVE updated_at (datetime)
      RENAME_SET_VALUE area_id > UF id (buffer)
      REMOVE import_id (int32)
      REMOVE region_name (buffer)
      REMOVE homes_passed_contractor_id (int32)
      REMOVE area_polygon_id (int32)
      REMOVE area_released_date (datetime)
      REMOVE pst_roll_out_end_date (datetime)
      REMOVE monday_board_id (buffer)
      REMOVE monday_group_id (buffer)
      REMOVE gf_project (varchar(255))
      REMOVE new_contractor_id (int32)
      REMOVE new_contractor_from (datetime)
      REMOVE ssv_contractor_id (int32)
    -> Junction_10
Note: Inspector : Input
Junction_10
    -> Junction_11

Bookmark: Apply validation results to SSV
AttributeManager
    ATTR_TABLE:
      SET_TO APP SSV BLDG GRP MAIN ADDRESS (buffer) = FME_CONDITIONAL:DEFAULT_VALUE'_FME_NO_OP_'BOOL_OP;OR;COMPOSITE_TEST;1;TEST SSV BLDG GRP MAIN ADDRESS CHK ATTRIBUTE_HAS_A_VALUE _FME_BLANK_STRING_'@Value(SSV BLDG GRP MAIN ADDRESS CHK)'FME_NUM_CONDITIONS2___
      SET_TO APP SSV BU COUNT (buffer) = FME_CONDITIONAL:DEFAULT_VALUE'_FME_NO_OP_'BOOL_OP;OR;COMPOSITE_TEST;1;TEST SSV BU COUNT CHK ATTRIBUTE_HAS_A_VALUE _FME_BLANK_STRING_'@Value(SSV BU COUNT CHK)'FME_NUM_CONDITIONS2___
      SET_TO APP SSV LU COUNT (buffer) = FME_CONDITIONAL:DEFAULT_VALUE'_FME_NO_OP_'BOOL_OP;OR;COMPOSITE_TEST;1;TEST SSV LU COUNT CHK ATTRIBUTE_HAS_A_VALUE _FME_BLANK_STRING_'@Value(SSV LU COUNT CHK)'FME_NUM_CONDITIONS2___
      SET_TO APP SSV TOTAL UNITS (buffer) = FME_CONDITIONAL:DEFAULT_VALUE'_FME_NO_OP_'BOOL_OP;OR;COMPOSITE_TEST;1;TEST SSV TOTAL UNITS CHK ATTRIBUTE_HAS_A_VALUE _FME_BLANK_STRING_'@Value(SSV TOTAL UNITS CHK)'FME_NUM_CONDITIONS2___
    -> Sorter
Sorter
    SORT_PARM = DMP POSTAL CODE NATURAL ASCENDING DMP STREET NATURAL ASCENDING DMP HOUSENUMBER NATURAL ASCENDING SSV VALIDATION STATUS NATURAL DESCENDING APP SSV TOTAL UNITS NATURAL DESCENDING
    SORTED -> DuplicateFilter_4
DuplicateFilter_4
    INPUT_ORDERED_CHOICE_LOOKUP = YES
    KEYATTR = DMP HOUSENUMBER DMP POSTAL CODE DMP STREET
    INPUT_ORDERED_CHOICE = Yes
    UNIQUE -> AttributeRemover
AttributeRemover
    REMOVE_ATTRS = ACT HP CY,ACT HP CY DEADLINE,ACT SSV CY,ACT SSV DEADLINE,ACT UNIFIBER,ACT UNIFIBER DATE,APP CCP SSV SU COUNT,APP CHK SU COUNT,APP PROCESSED,Audit report,Audit report date,BLD ALL READY STATUS,BLD COMPANY,BLD FIBER BLOWN ACTUAL DATE,BLD FIBER BLOWN PLANNED DATE,BLD FIBER BLOWN STATUS,BLD FIBER SPLICED ACTUAL DATE,BLD FIBER SPLICED PLANNED DATE,BLD FIBER SPLICED STATUS,BLD INTRO ACTUAL DATE,BLD INTRO PLANNED DATE,BLD INTRO STATUS,BLD SSV USABILITY,BLD VC ACTUAL DATE,BLD VC PLANNED DATE,BLD VC STATUS,Building Group Check,Cable/material trajectory,CCP CHECK DONE,CCP CLEANUP COMMENT,CCP cleanup scope,CCP SSV BU COUNT,CCP SSV LOW FLOOR,CCP SSV LU COUNT,CCP SSV QUADRANT,CCP SSV TOTAL UNITS,CCP SSV UPPER FLOOR,CHK SSV BU COUNT,CHK SSV DOC LINK,CHK SSV LU COUNT,CHK SSV QUADRANT,CHK SSV TOTAL UNITS,CHK SSV UPPER FLOOR,CHK TSA DOC FOR SIGNATURE,CHK TSA DOC SIGNED,CHK TSA STATUS,Contact Details,item_id,Picture Quality,PRIORITY,PST CENTRAL POP STATUS,PST DEL HCA,PST DEL STAT CODE DESC,PST HP ACTUAL DATE,PST HP PLANNED DATE,Quadrant Design,SSV ACTUAL DATE,SSV AGENT,SSV BLDG GRP MAIN ADDRESS CHK,SSV BLOCK,SSV BU COUNT CHK,SSV DOC LINK,SSV LU COUNT CHK,SSV PLANNED DATE,SSV REGISTRATION STATUS,SSV STATUS,SSV SU COUNT CHK,SSV SYNDIC,SSV SYNDIC MAIL,SSV SYNDIC NAME,SSV SYNDIC PHONE,SSV TIMESTAMP,SSV TOTAL UNITS CHK,SSV validation counter,SSV validation date,SSV VALIDATION STATUS,SSV VALIDATOR,STS ACTUAL DATE,STS DOC LINK,STS PARTNER,STS PLANNED DATE,STS QUADRANT,STS STATUS,STS UNITS COUNT,TSA 1ST REMINDER DATE,TSA 2ND REMINDER DATE,TSA 3RD REMINDER DATE,TSA 4TH REMINDER DATE,TSA DOC FOR SIGNATURE,TSA DOC SIGNED,TSA GENERAL ASSEMBLY DATE,TSA NEGOTIATOR,TSA NEGOTIATOR COMMENTS,TSA READY TO SEND DATE,TSA REFUSED DATE,TSA REGISTRATION STATUS,TSA SENT DATE,TSA SIGNED DATE,TSA STATUS,TSA validation counter,TSA validation date,TSA VALIDATION STATUS,VALIDATION COMMENT SSV,VALIDATION COMMENT TSA
    -> AttributeManager_5
    -> AttributeManager_3
    -> FeatureJoiner_7 [RIGHT]
    -> FeatureJoiner [RIGHT]

Bookmark: Applying main address info
AttributeManager_3
    ATTR_TABLE:
      SET_TO Task_no mun (varchar(200)) = @Value(DMP CITY)_@Value(DMP STREET)_@Value(DMP HOUSENUMBER)
      SET_TO Task_no _ (varchar(200)) = @Value(DMP CITY)@Value(DMP STREET)@Value(DMP HOUSENUMBER)
      SET_TO Task_last (varchar(200)) = @Value(DMP MUNICIPALITY)_@Value(DMP STREET)_@Value(DMP HOUSENUMBER)
    -> FeatureJoiner_3 [RIGHT]
    -> FeatureJoiner_4 [RIGHT]
    -> FeatureJoiner_5 [RIGHT]
    -> FeatureJoiner_6 [RIGHT]
TestFilter_2
    DEFAULT_VALUE = <UNFILTERED>
    PASSED_TEST_GROUP_OUTPUT = FIRST
    TEST_LIST = "BOOL_OP,OR,COMPOSITE_TEST,""""""1"""""",TEST_CLAUSE,TEST building_group ATTRIBUTE_HAS_A_VALUE """,building_group ATTRIBUTE_HAS_A_VALUE
    building_group ATTRIBUTE_HAS_A_VALUE -> FeatureJoiner_3 [LEFT]
    <UNFILTERED> -> FeatureJoiner_2 [LEFT]
FeatureJoiner_3
    ATTR_CONFLICT_RES_LOOKUP = USE_LEFT
    GEOMETRY_HANDLING_LOOKUP = USE_LEFT
    JOIN_KEYS = building_group task AUTO
    JOIN_MODE = Inner
    ATTR_CONFLICT_RES = Prefer Left
    GEOMETRY_HANDLING = Prefer Left
    JOINED -> Correcting_BG_Group
    UNJOINED_LEFT -> FeatureJoiner_4 [LEFT]
FeatureJoiner_4
    ATTR_CONFLICT_RES_LOOKUP = USE_LEFT
    GEOMETRY_HANDLING_LOOKUP = USE_LEFT
    JOIN_KEYS = building_group Task_no mun AUTO
    JOIN_MODE = Inner
    ATTR_CONFLICT_RES = Prefer Left
    GEOMETRY_HANDLING = Prefer Left
    JOINED -> Correcting_BG_Group
    UNJOINED_LEFT -> FeatureJoiner_5 [LEFT]
FeatureJoiner_5
    ATTR_CONFLICT_RES_LOOKUP = USE_LEFT
    GEOMETRY_HANDLING_LOOKUP = USE_LEFT
    JOIN_KEYS = building_group Task_no _ AUTO
    JOIN_MODE = Inner
    ATTR_CONFLICT_RES = Prefer Left
    GEOMETRY_HANDLING = Prefer Left
    JOINED -> Correcting_BG_Group
    UNJOINED_LEFT -> FeatureJoiner_6 [LEFT]
FeatureJoiner_6
    ATTR_CONFLICT_RES_LOOKUP = USE_LEFT
    GEOMETRY_HANDLING_LOOKUP = USE_LEFT
    JOIN_KEYS = building_group Task_last AUTO
    JOIN_MODE = Inner
    ATTR_CONFLICT_RES = Prefer Left
    GEOMETRY_HANDLING = Prefer Left
    JOINED -> Correcting_BG_Group
Correcting_BG_Group: AttributeManager
    ATTR_TABLE:
      SET_TO street_name (buffer) = @Value(DMP STREET)
      SET_TO house_number (buffer) = @Value(DMP HOUSENUMBER)
      SET_TO house_number_extension (buffer) = @Value(DMP HOUSENUMBER)
      SET_TO postal_code (buffer) = @Value(DMP POSTAL CODE)
      SET_TO municipality (buffer) = @Value(DMP MUNICIPALITY)
      SET_TO city (buffer) = @Value(DMP CITY)
      SET_TO building_group (buffer) = @Value(task)
      REMOVE DMP AREA AREA ID (buffer)
      REMOVE DMP AREA NAME (buffer)
      RENAME_SET_VALUE DMP POSTAL CODE > MBG POSTAL CODE (buffer)
      RENAME_SET_VALUE DMP MUNICIPALITY > MBG MUNICIPALITY (buffer)
      RENAME_SET_VALUE DMP CITY > MBG CITY (buffer)
      RENAME_SET_VALUE DMP STREET > MBG STREET (buffer)
      RENAME_SET_VALUE DMP HOUSENUMBER > MBG HOUSENUMBER (buffer)
      RENAME_SET_VALUE DMP BUILDING KEY > MBG BUILDING KEY (buffer)
      RENAME_SET_VALUE DMP BELMAP LU COUNT > MBG BELMAP LU COUNT (buffer)
      REMOVE DMP POP AREA NAME (buffer)
      REMOVE DMP IN SCOPE (buffer)
      REMOVE APP SSV BLDG GRP INDIV TREATMENT (buffer)
      REMOVE APP SSV BLDG GRP MAIN ADDRESS (buffer)
      REMOVE APP SSV BU COUNT (buffer)
      REMOVE APP SSV BUILDING GROUP (buffer)
      REMOVE APP SSV BUILDING TYPE (buffer)
      REMOVE APP SSV DEPLOYMENT TYPE (buffer)
      REMOVE APP SSV LOW FLOOR (buffer)
      REMOVE APP SSV LU COUNT (buffer)
      REMOVE APP SSV QUADRANT (buffer)
      REMOVE APP SSV SU COUNT (buffer)
      REMOVE APP SSV TOTAL UNITS (buffer)
      REMOVE APP SSV UPPER FLOOR (buffer)
      REMOVE DMP LOCATION CHK (buffer)
      REMOVE Task_no mun (varchar(200))
      REMOVE Task_no _ (varchar(200))
      REMOVE Task_last (varchar(200))
    -> AttributeManager_4

Bookmark: Linking Address with SSV
AttributeManager_5
    -> FeatureJoiner_2 [RIGHT]
AttributeManager_4
    ATTR_TABLE:
      SET_TO belmap_building_id (int32) = @Value(MBG BUILDING KEY)
      SET_TO street_name (buffer) = @Value(MBG STREET)
      SET_TO house_number_extension (buffer) = @Value(MBG HOUSENUMBER)
      SET_TO postal_code (buffer) = @Value(MBG POSTAL CODE)
      SET_TO municipality (buffer) = @Value(MBG MUNICIPALITY)
      SET_TO city (buffer) = @Value(MBG CITY)
    -> AttributeRemover_3
AttributeRemover_3
    REMOVE_ATTRS = MBG BELMAP LU COUNT,MBG BUILDING KEY,MBG CITY,MBG HOUSENUMBER,MBG MUNICIPALITY,MBG POSTAL CODE,MBG STREET
    -> FeatureJoiner_2 [LEFT]
FeatureJoiner_2
    ATTR_CONFLICT_RES_LOOKUP = USE_LEFT
    GEOMETRY_HANDLING_LOOKUP = USE_LEFT
    JOIN_KEYS = street_name DMP STREET AUTO postal_code DMP POSTAL CODE AUTO house_number_extension DMP HOUSENUMBER AUTO
    JOIN_MODE = Inner
    ATTR_CONFLICT_RES = Prefer Left
    GEOMETRY_HANDLING = Prefer Left
    JOINED -> DuplicateFilter
    UNJOINED_LEFT -> DuplicateFilter
DuplicateFilter
    INPUT_ORDERED_CHOICE_LOOKUP = NO
    KEYATTR = jvid
    INPUT_ORDERED_CHOICE = No
    UNIQUE -> BL_2
    UNIQUE -> DL_2

Bookmark: Address to DL
TestFilter_4
    DEFAULT_VALUE = <UNFILTERED>
    PASSED_TEST_GROUP_OUTPUT = FIRST
    TEST_LIST:
      "BOOL_OP,AND,COMPOSITE_TEST,""""""1 AND 2 AND 3 AND 4"""""",TEST_CLAUSE,TEST scopelist_v15 ATTRIBUTE_HAS_A_VALUE ""
      TEST out_of_scope_at ATTRIBUTE_VALUE_NULL ""
      TEST deleted_at ATTRIBUTE_VALUE_NULL ""
      TEST scopelist_v2 ATTRIBUTE_VALUE_NULL """,Delta DL
    Delta DL -> TestFilter_7
TestFilter_7
    DEFAULT_VALUE = <UNFILTERED>
    PASSED_TEST_GROUP_OUTPUT = FIRST
    TEST_LIST:
      "BOOL_OP,AND,COMPOSITE_TEST,""""""1 AND 2"""""",TEST_CLAUSE,TEST twin_jvid ATTRIBUTE_HAS_A_VALUE ""
      TEST @Value(dwelling_unit_type) = SDU",twin_jvid ATTRIBUTE_HAS_A_VALUE
    twin_jvid ATTRIBUTE_HAS_A_VALUE -> AttributeCreator_4
    <UNFILTERED> -> TestFilter_9
TestFilter_9
    DEFAULT_VALUE = <UNFILTERED>
    PASSED_TEST_GROUP_OUTPUT = FIRST
    TEST_LIST:
      "BOOL_OP,AND,COMPOSITE_TEST,""""""1 AND 2"""""",TEST_CLAUSE,TEST @Value(dwelling_unit_type) = SDU
      TEST building_group ATTRIBUTE_VALUE_NULL """,@Value(dwelling_unit_type) = SDU
    @Value(dwelling_unit_type) = SDU -> AttributeCreator_5

Bookmark: Know New SDU
AttributeCreator_4
    ATTR_TABLE = SET_TO Type (varchar(24)) = Has a twin
    -> AttributeManager_9
AttributeManager_9
    ATTR_TABLE = REMOVE type (buffer)
    -> Junction_4
Note: With_Twin : Input
Junction_4
    -> Junction_7
AttributeCreator_5
    ATTR_TABLE = SET_TO Type (varchar(24)) = SDU
    -> AttributeManager_10
AttributeManager_10
    ATTR_TABLE = REMOVE type (buffer)
    -> Junction_8
Note: Without twin : Input
Junction_8
    -> Junction_9

Bookmark: Summary sums
With_Twin: Inspector [off]
Note: Should have a twin defined!
SDU: Inspector [off]
Excessive_LU: Aggregator
    ACCUM_ATTRS_NAME = Drop Incoming Attributes
    AGGREGATE_TYPE = Homogeneous Collection (If Possible)
    MODE = Geometry - Assemble One Level
    SEP = ,
    SUM = "Excessive LU - BU" "Excessive LU - DL"
    AGGREGATE -> AttributeManager_15
LU_to_review: Aggregator
    ACCUM_ATTRS_NAME = Drop Incoming Attributes
    AGGREGATE_TYPE = Homogeneous Collection (If Possible)
    COUNT_ATTR = count
    MODE = Geometry - Assemble One Level
    SEP = ,
    SUM = "Potential LU - BL" "Potential LU - DL"
    AGGREGATE -> AttributeManager_14
Note: Certaines LU sont déjà dans DL, comment flagger? nécessaire?
LU_to_DL: Aggregator
    ACCUM_ATTRS_NAME = Drop Incoming Attributes
    AGGREGATE_TYPE = Homogeneous Collection (If Possible)
    COUNT_ATTR = count
    MODE = Geometry - Assemble One Level
    SEP = ,
    SUM = "Potential LU - BL" "Potential LU - DL"
    AGGREGATE -> AttributeManager_13
New_SDU: Inspector [off]

Bookmark: Building Groups to JVIDs
FeatureJoiner
    ATTR_CONFLICT_RES_LOOKUP = USE_LEFT
    GEOMETRY_HANDLING_LOOKUP = USE_LEFT
    JOIN_KEYS = street_name DMP STREET AUTO house_number_extension DMP HOUSENUMBER AUTO postal_code DMP POSTAL CODE AUTO
    JOIN_MODE = Inner
    ATTR_CONFLICT_RES = Prefer Left
    GEOMETRY_HANDLING = Prefer Left
    JOINED -> TestFilter
    UNJOINED_LEFT -> DuplicateFilter_3
TestFilter
    DEFAULT_VALUE = <UNFILTERED>
    PASSED_TEST_GROUP_OUTPUT = FIRST
    TEST_LIST = "BOOL_OP,OR,COMPOSITE_TEST,""""""1"""""",TEST_CLAUSE,TEST @Value(APP SSV TOTAL UNITS) = 0",Need a main
    Need a main -> AttributeManager_2
    <UNFILTERED> -> AttributeRemover_2
AttributeManager_2
    ATTR_TABLE = SET_TO building_group (buffer) = FME_CONDITIONAL:DEFAULT_VALUE'_FME_NO_OP_'BOOL_OP;OR;COMPOSITE_TEST;1;TEST APP SSV BLDG GRP MAIN ADDRESS ATTRIBUTE_HAS_A_VALUE _FME_BLANK_STRING_'@Value(APP SSV BLDG GRP MAIN ADDRESS)'FME_NUM_CONDITIONS2___
    -> AttributeRemover_2
AttributeRemover_2
    REMOVE_ATTRS = APP SSV BLDG GRP INDIV TREATMENT,APP SSV BLDG GRP MAIN ADDRESS,APP SSV BU COUNT,APP SSV BUILDING GROUP,APP SSV BUILDING TYPE,APP SSV DEPLOYMENT TYPE,APP SSV LOW FLOOR,APP SSV LU COUNT,APP SSV QUADRANT,APP SSV SU COUNT,APP SSV TOTAL UNITS,APP SSV UPPER FLOOR,DMP AREA AREA ID,DMP AREA NAME,DMP BELMAP LU COUNT,DMP BUILDING KEY,DMP CITY,DMP HOUSENUMBER,DMP IN SCOPE,DMP LOCATION CHK,DMP MUNICIPALITY,DMP POP AREA NAME,DMP POSTAL CODE,DMP STREET,task
    -> DuplicateFilter_3

Bookmark: Build list and deployment list count per MDU
BL_2: TestFilter
    DEFAULT_VALUE = <UNFILTERED>
    PASSED_TEST_GROUP_OUTPUT = FIRST
    TEST_LIST = "BOOL_OP,OR,COMPOSITE_TEST,""""""1"""""",TEST_CLAUSE,TEST scopelist_v2 ATTRIBUTE_HAS_A_VALUE """,BL
    BL -> Aggregator
Aggregator
    ACCUM_ATTRS_NAME = Drop Incoming Attributes
    AGGREGATE_TYPE = Homogeneous Collection (If Possible)
    COUNT_ATTR = Count_BL
    GROUP_BY = city house_number_extension street_name postal_code
    MODE = Geometry - Assemble One Level
    SEP = ,
    AGGREGATE -> FeatureJoiner_8 [LEFT]
DL_2: TestFilter
    DEFAULT_VALUE = <UNFILTERED>
    PASSED_TEST_GROUP_OUTPUT = FIRST
    TEST_LIST:
      "BOOL_OP,AND,COMPOSITE_TEST,""""""1 AND 2 AND 3"""""",TEST_CLAUSE,TEST scopelist_v15 ATTRIBUTE_HAS_A_VALUE ""
      TEST out_of_scope_at ATTRIBUTE_VALUE_NULL ""
      TEST deleted_at ATTRIBUTE_VALUE_NULL """,DL
    DL -> Aggregator_2
Aggregator_2
    ACCUM_ATTRS_NAME = Drop Incoming Attributes
    AGGREGATE_TYPE = Homogeneous Collection (If Possible)
    CONCAT_ATTRS = delivery_status jvid status bus_number
    COUNT_ATTR = Count_DL
    GROUP_BY = city house_number_extension street_name postal_code
    MODE = Geometry - Assemble One Level
    SEP = ,
    AGGREGATE -> FeatureJoiner_8 [RIGHT]
FeatureJoiner_8
    ATTR_CONFLICT_RES_LOOKUP = USE_LEFT
    GEOMETRY_HANDLING_LOOKUP = USE_LEFT
    JOIN_KEYS = city city AUTO street_name street_name AUTO house_number_extension house_number_extension AUTO postal_code postal_code AUTO
    JOIN_MODE = Inner
    ATTR_CONFLICT_RES = Prefer Left
    GEOMETRY_HANDLING = Prefer Left
    JOINED -> FeatureJoiner_7 [LEFT]
    UNJOINED_LEFT -> AttributeCreator
    UNJOINED_RIGHT -> AttributeCreator_2
AttributeCreator
    ATTR_TABLE = SET_TO Count_DL (uint8) = 0
    -> FeatureJoiner_7 [LEFT]
AttributeCreator_2
    ATTR_TABLE = SET_TO Count_BL (uint8) = 0
    -> FeatureJoiner_7 [LEFT]
FeatureJoiner_7
    ATTR_CONFLICT_RES_LOOKUP = USE_LEFT
    GEOMETRY_HANDLING_LOOKUP = USE_LEFT
    JOIN_KEYS = street_name DMP STREET AUTO postal_code DMP POSTAL CODE AUTO house_number_extension DMP HOUSENUMBER AUTO
    JOIN_MODE = Inner
    ATTR_CONFLICT_RES = Prefer Left
    GEOMETRY_HANDLING = Prefer Left
    JOINED -> TestFilter_3

Bookmark: Comparison SSV - BL
TestFilter_3
    DEFAULT_VALUE = <UNFILTERED>
    PASSED_TEST_GROUP_OUTPUT = FIRST
    TEST_LIST = "BOOL_OP,OR,COMPOSITE_TEST,""""""1"""""",TEST_CLAUSE,TEST APP SSV TOTAL UNITS ATTRIBUTE_HAS_A_VALUE """,APP SSV TOTAL UNITS ATTRIBUTE_HAS_A_VALUE
    APP SSV TOTAL UNITS ATTRIBUTE_HAS_A_VALUE -> SSV_compared_to_BL
SSV_compared_to_BL: TestFilter
    DEFAULT_VALUE = <UNFILTERED>
    PASSED_TEST_GROUP_OUTPUT = FIRST
    TEST_LIST = "BOOL_OP,OR,COMPOSITE_TEST,""""""1"""""",TEST_CLAUSE,TEST @sum(@Value(APP SSV LU COUNT),@Value(APP SSV BU COUNT)) < @Value(Count_BL)",SSV < DMP,"BOOL_OP,OR,COMPOSITE_TEST,""""""1"""""",TEST_CLAUSE,TEST @sum(@Value(APP SSV LU COUNT),@Value(APP SSV BU COUNT)) = @Value(Count_BL)",SSV = DMP,"BOOL_OP,OR,COMPOSITE_TEST,""""""1"""""",TEST_CLAUSE,TEST @sum(@Value(APP SSV LU COUNT),@Value(APP SSV BU COUNT)) > @Value(Count_BL)",SSV > DMP
    SSV < DMP -> TestFilter_6
    SSV > DMP -> AttributeManager_7
    SSV > DMP -> SSV_compared_to_DL

Bookmark: Wirte to summary file
AttributeManager_15
    ATTR_TABLE:
      SET_TO UF id (varchar(200)) = $(DMP_Area_Area_ID)
      RENAME_SET_VALUE Excessive LU - BU > Excessive LU (real64)
      REMOVE Excessive LU - DL (real64)
    -> FeatureJoiner_14 [LEFT]
AttributeManager_14
    ATTR_TABLE:
      RENAME_SET_VALUE Potential LU - BL > LU to review (real64)
      REMOVE Potential LU - DL (real64)
      REMOVE count (uint32)
      SET_TO UF id (varchar(200)) = $(DMP_Area_Area_ID)
    -> FeatureJoiner_14 [RIGHT]
FeatureJoiner_14
    ATTR_CONFLICT_RES_LOOKUP = USE_LEFT
    GEOMETRY_HANDLING_LOOKUP = USE_LEFT
    JOIN_KEYS = UF id UF id AUTO
    JOIN_MODE = Inner
    ATTR_CONFLICT_RES = Prefer Left
    GEOMETRY_HANDLING = Prefer Left
    JOINED -> FeatureJoiner_15 [LEFT]
AttributeManager_13
    ATTR_TABLE:
      RENAME_SET_VALUE Potential LU - BL > LU to DL (real64)
      REMOVE Potential LU - DL (real64)
      REMOVE count (uint32)
      SET_TO UF id (varchar(200)) = $(DMP_Area_Area_ID)
    -> FeatureJoiner_15 [RIGHT]
FeatureJoiner_15
    ATTR_CONFLICT_RES_LOOKUP = USE_LEFT
    GEOMETRY_HANDLING_LOOKUP = USE_LEFT
    JOIN_KEYS = UF id UF id AUTO
    JOIN_MODE = Inner
    ATTR_CONFLICT_RES = Prefer Left
    GEOMETRY_HANDLING = Prefer Left
    JOINED -> FeatureJoiner_13 [RIGHT]
Note: Aggregator_4 : Aggregate
Junction_13
    -> FeatureJoiner_16 [LEFT]
Note: AttributeManager_12 : Output
Junction_11
    -> FeatureJoiner_13 [LEFT]
FeatureJoiner_13
    ATTR_CONFLICT_RES_LOOKUP = USE_LEFT
    GEOMETRY_HANDLING_LOOKUP = USE_LEFT
    JOIN_KEYS = UF id UF id AUTO
    JOIN_MODE = Inner
    ATTR_CONFLICT_RES = Prefer Left
    GEOMETRY_HANDLING = Prefer Left
    JOINED -> FeatureJoiner_16 [RIGHT]
FeatureJoiner_16
    ATTR_CONFLICT_RES_LOOKUP = USE_LEFT
    GEOMETRY_HANDLING_LOOKUP = USE_LEFT
    JOIN_KEYS = UF id UF id AUTO
    JOIN_MODE = Inner
    ATTR_CONFLICT_RES = Prefer Left
    GEOMETRY_HANDLING = Prefer Left
    JOINED -> FeatureJoiner_17 [RIGHT]
FeatureJoiner_17
    ATTR_CONFLICT_RES_LOOKUP = USE_LEFT
    GEOMETRY_HANDLING_LOOKUP = USE_LEFT
    JOIN_KEYS = UF id UF id AUTO
    JOIN_MODE = Inner
    ATTR_CONFLICT_RES = Prefer Left
    GEOMETRY_HANDLING = Prefer Left
    JOINED -> AttributeCreator_9
AttributeCreator_9
    ATTR_TABLE = SET_TO Delta (varchar(200)) = @sub(@Value(BL_v2),@Value(BL_v1))
    -> FeatureWriter_4 [Joined]
FeatureWriter_4
    DATASET = $(FME_MF_DIR_ENCODED)Outputs\BL-SSV deltas.xlsx
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = No
    XLSXW_PROTECT_SHEET = NO
    XLSXW_RASTER_FORMAT = PNG
    XLSXW_STRICT_SCHEMA_ADDITIONAL_ATTRIBUTE_MATCHING = yes
    XLSXW_TRUNCATE_TABLE = No
    XLSXW_WRITER_MODE = Insert

Bookmark: Build list and deployment list
BL: TestFilter
    DEFAULT_VALUE = <UNFILTERED>
    PASSED_TEST_GROUP_OUTPUT = FIRST
    TEST_LIST = "BOOL_OP,OR,COMPOSITE_TEST,""""""1"""""",TEST_CLAUSE,TEST scopelist_v2 ATTRIBUTE_HAS_A_VALUE """,BL
    BL -> Remove2001_2
    BL -> Aggregator_4
DL: TestFilter
    DEFAULT_VALUE = <UNFILTERED>
    PASSED_TEST_GROUP_OUTPUT = FIRST
    TEST_LIST:
      "BOOL_OP,AND,COMPOSITE_TEST,""""""1 AND 2 AND 3"""""",TEST_CLAUSE,TEST scopelist_v15 ATTRIBUTE_HAS_A_VALUE ""
      TEST out_of_scope_at ATTRIBUTE_VALUE_NULL ""
      TEST deleted_at ATTRIBUTE_VALUE_NULL """,DL
    DL -> FeatureJoiner_12 [RIGHT]

Bookmark: More than 1 status
Remove2001_2: TestFilter
    DEFAULT_VALUE = <UNFILTERED>
    PASSED_TEST_GROUP_OUTPUT = FIRST
    TEST_LIST = "BOOL_OP,OR,COMPOSITE_TEST,""""""1"""""",TEST_CLAUSE,TEST @Value(delivery_status) = 2001",Address doesn't exist
    <UNFILTERED> -> Aggregator_5
Aggregator_5
    ACCUM_ATTRS_NAME = Merge Incoming Attributes
    COUNT_ATTR = Count_BL
    GROUP_BY = house_number_extension postal_code street_name
    LIST_ATTRS_TO_INCLUDE = delivery_status
    LIST_NAME = DS_MDU
    MODE = Attributes Only
    SEP = ,
    AGGREGATE -> ListDuplicateRemover_2
ListDuplicateRemover_2
    SRC_LIST = DS_MDU{}.delivery_status
    -> ListElementCounter_2
ListElementCounter_2
    CNT_ATTR = UniqueDS
    LIST_NAME = DS_MDU{}
    -> TestFilter_8
TestFilter_8
    DEFAULT_VALUE = <UNFILTERED>
    PASSED_TEST_GROUP_OUTPUT = FIRST
    TEST_LIST = "BOOL_OP,OR,COMPOSITE_TEST,""""""1"""""",TEST_CLAUSE,TEST @Value(UniqueDS) > 1",@Value(UniqueDS) > 1
    <UNFILTERED> -> AttributeManager_6
AttributeManager_6
    ATTR_TABLE:
      REMOVE id (int32)
      REMOVE area_id (int32)
      REMOVE surveyed_by_id (int32)
      REMOVE created_at (datetime)
      REMOVE updated_at (datetime)
      REMOVE jvid (int32)
      REMOVE jvid_use (varchar(255))
      REMOVE belmap_address_id (int32)
      REMOVE house_number (buffer)
      REMOVE bus_number (buffer)
      REMOVE appartment_number (buffer)
      REMOVE municipality (buffer)
      REMOVE building_type (varchar(255))
      REMOVE city (buffer)
      REMOVE x (real64)
      REMOVE y (real64)
      REMOVE home_released (logical)
      REMOVE home_released_date (datetime)
      REMOVE survey_status (varchar(255))
      REMOVE survey_date (datetime)
      REMOVE status (varchar(255))
      REMOVE service_type (buffer)
      REMOVE address_source (varchar(255))
      RENAME_SET_VALUE delivery_status > DMP_delivery_status (int32)
      REMOVE reason_not_homes_passed (int32)
      REMOVE dwelling_unit_type (varchar(255))
      REMOVE building_use (buffer)
      REMOVE lot (buffer)
      REMOVE distribution_point_number (buffer)
      REMOVE dependency_of_others (int32)
      REMOVE homes_passed_plan_date (datetime)
      REMOVE homes_passed_actual_date (datetime)
      REMOVE civil_plan_date (datetime)
      REMOVE installation_type (varchar(255))
      REMOVE length_estimate_from_street (int32)
      REMOVE existing_duct_frontyard (buffer)
      REMOVE lat (real64)
      REMOVE lon (real64)
      REMOVE amount_of_meters_dug (int32)
      REMOVE cocon_frame (buffer)
      REMOVE quadrant (buffer)
      REMOVE deleted_at (datetime)
      REMOVE street_survey_distribution_way (varchar(255))
      REMOVE homes_connect_at (datetime)
      REMOVE internal_remarks (buffer)
      REMOVE action_needed (logical)
      REMOVE capakey (buffer)
      REMOVE nis5 (int32)
      REMOVE nis9 (buffer)
      REMOVE preferred_distribution (buffer)
      REMOVE hc_type (buffer)
      REMOVE hc_length (int32)
      REMOVE num_floor (int32)
      REMOVE area_pop_id (int32)
      REMOVE central_pop_id (int32)
      REMOVE scopelist_v0 (date)
      REMOVE scopelist_v15 (date)
      REMOVE scopelist_v2 (date)
      REMOVE first_hp_wip (date)
      REMOVE first_hp_hca (date)
      REMOVE sub_address_of (int32)
      REMOVE belmap_version (int32)
      REMOVE home_release_blocked_at (datetime)
      REMOVE home_release_blocked_reason (varchar(255))
      REMOVE main_address (logical)
      REMOVE fiberzone (buffer)
      REMOVE house_entry_deploy_type (varchar(255))
      REMOVE approved_for_release (logical)
      REMOVE home_release_reverted_at (datetime)
      REMOVE quadrant_pst (buffer)
      REMOVE out_of_scope_at (datetime)
      REMOVE ftu_location (buffer)
      REMOVE mdu_ssv (buffer)
      REMOVE quote_approved (logical)
      REMOVE pst_update_blocked (logical)
      REMOVE home_release_blocked_by_delay_id (int32)
      REMOVE batch (buffer)
      REMOVE building_group (buffer)
      REMOVE type (buffer)
      REMOVE distance_source (buffer)
      REMOVE pst_update_blocked_reason (buffer)
      REMOVE amount_of_meters_aerial (int32)
      REMOVE amount_of_meters_facade (int32)
      REMOVE homes_passed_wip_actual_date (datetime)
      REMOVE ftu_floor (int32)
      REMOVE ftu_location_other (buffer)
      REMOVE ftu_other_room (logical)
      REMOVE excavation_above (int32)
      REMOVE quote_reference (buffer)
      REMOVE quote_required (buffer)
      REMOVE asphalt (logical)
      REMOVE twin_jvid (int32)
      REMOVE DS_MDU{}.delivery_status (int32)
      REMOVE Count_BL (uint32)
      REMOVE UniqueDS (uint64)
      REMOVE sdu_exceptional (logical)
      REMOVE meters_public (int64)
      REMOVE meters_private (int64)
      REMOVE meters_indoor (int64)
      REMOVE meters_existing_drop (int64)
    -> FeatureJoiner_9 [LEFT]

Bookmark: New SDU
TestFilter_10
    DEFAULT_VALUE = Main
    PASSED_TEST_GROUP_OUTPUT = FIRST
    TEST_LIST:
      "BOOL_OP,AND,COMPOSITE_TEST,""""""1 AND 2"""""",TEST_CLAUSE,TEST @Value(main_address) = f
      TEST @Value(dwelling_unit_type) = SDU",Child and SDU
    Child and SDU -> FeatureJoiner_10 [LEFT]
FeatureJoiner_10
    ATTR_CONFLICT_RES_LOOKUP = USE_LEFT
    GEOMETRY_HANDLING_LOOKUP = USE_LEFT
    JOIN_KEYS = addr_key belmap_address_id AUTO
    JOIN_MODE = Inner
    ATTR_CONFLICT_RES = Prefer Left
    GEOMETRY_HANDLING = Prefer Left
    JOINED -> TestFilter_11
    UNJOINED_LEFT -> FeatureJoiner_11 [LEFT]
TestFilter_11
    DEFAULT_VALUE = New SDU
    PASSED_TEST_GROUP_OUTPUT = FIRST
    TEST_LIST:
      "BOOL_OP,OR,COMPOSITE_TEST,""""""1 OR 2"""""",TEST_CLAUSE,TEST scopelist_v15 ATTRIBUTE_HAS_A_VALUE ""
      TEST scopelist_v2 ATTRIBUTE_HAS_A_VALUE """,In SL,"BOOL_OP,OR,COMPOSITE_TEST,""""""1"""""",TEST_CLAUSE,TEST out_of_scope_at ATTRIBUTE_HAS_A_VALUE """,out_of_scope
    New SDU -> FeatureJoiner_11 [LEFT]
FeatureJoiner_11
    ATTR_CONFLICT_RES_LOOKUP = USE_RIGHT
    GEOMETRY_HANDLING_LOOKUP = USE_LEFT
    JOIN_KEYS = street_nm street_name AUTO hnr_full house_number_extension AUTO pc postal_code AUTO
    JOIN_MODE = Inner
    ATTR_CONFLICT_RES = Prefer Right
    GEOMETRY_HANDLING = Prefer Left
    JOINED -> TestFilter_12
    <REJECTED> -> FeatureJoiner_11__Rejected_
FeatureJoiner_11__Rejected_: Inspector [off]
TestFilter_12
    DEFAULT_VALUE = New SDU
    PASSED_TEST_GROUP_OUTPUT = FIRST
    TEST_LIST:
      "BOOL_OP,OR,COMPOSITE_TEST,""""""1 OR 2"""""",TEST_CLAUSE,TEST scopelist_v15 ATTRIBUTE_HAS_A_VALUE ""
      TEST scopelist_v2 ATTRIBUTE_HAS_A_VALUE """,In SL,"BOOL_OP,OR,COMPOSITE_TEST,""""""1"""""",TEST_CLAUSE,TEST out_of_scope_at ATTRIBUTE_HAS_A_VALUE """,out_of_scope
    New SDU -> DuplicateFilter_2
DuplicateFilter_2
    INPUT_ORDERED_CHOICE_LOOKUP = NO
    KEYATTR = addr_key
    INPUT_ORDERED_CHOICE = No
    UNIQUE -> Junction_2
Note: New_SDU : Input
Junction_2
    -> Junction_3

Bookmark: Outputs
FeatureWriter_2 [off]
    DATASET = $(FME_MF_DIR_ENCODED)Outputs\Ottignies - SSV_Integration.xlsx
    DATASET_ATTR = _dataset
    FEATURE_TYPE_LIST_ATTR = _feature_types
    FORMAT = XLSXW
    TOTAL_FEATURES_WRITTEN_ATTR = _total_features_written
    XLSXW_COORDINATE_SYSTEM_GRANULARITY = FEATURE_TYPE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert
FeatureWriter [off]
    DATASET = $(FME_MF_DIR_ENCODED)Outputs\Ottignies - SSV_Integration.gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = YES
    OGCGEOPACKAGE_TRANSACTION_SIZE = 5000
    OGCGEOPACKAGE_VERSION = 1.2
    OGCGEOPACKAGE_WRITE_NULLS = YES
    TOTAL_FEATURES_WRITTEN_ATTR = _total_features_written
