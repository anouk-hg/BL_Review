FME workspace BL-DL-SSV_Rework_v1.fmw

Parameters:
- SourceDataset_POSTGIS = Unifiber - AH   # Connection
- DMP_Area_Area_ID = UF004-01   # DMP AREA AREA ID
- Area_ID = 16

Readers:
- POSTGIS_1: POSTGIS from $(SourceDataset_POSTGIS)

DuplicateFilter
    INPUT_ORDERED_CHOICE_LOOKUP = NO
    KEYATTR = task
    INPUT_ORDERED_CHOICE = No
    UNIQUE -> Counter_2
FeatureJoiner_6__Rejected_: Inspector [off]
FeatureWriter_2
    CONFIG_PARAMETERS = ESCAPE_COMMAS_IN_FTP_FORMAT_PARAMETERS,no
    DATASET = $(FME_MF_DIR_ENCODED)Outputs\BL Review\$(DMP_Area_Area_ID).xlsx
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert
AttributeManager_4
    ATTR_TABLE:
      RENAME_SET_VALUE $(Area_ID) > Area_ID (varchar(200)) = $(Area_ID)
      RENAME_SET_VALUE $(DMP_Area_Area_ID) > DMP_Area_Area_ID (varchar(200)) = $(DMP_Area_Area_ID)
    USER_EXPOSED_ATTRIBUTES = $(Area_ID),$(DMP_Area_Area_ID)
    -> FeatureJoiner_7 [RIGHT]
AttributeFilter
    ATTR_NAME = action
    ATTR_VALUES = <Empty>,<Missing>,<Null>,<Unfiltered>,ADD,KEEP,REMOVE
    ADD -> FeatureJoiner_10 [LEFT]
FeatureJoiner_10
    ATTR_CONFLICT_RES = USE_LEFT
    GEOMETRY_HANDLING = USE_LEFT
    JOIN_KEYS = MDU_ID MDU_ID AUTO
    JOIN_MODE = Inner
    JOINED -> Template_for_Streetsurvey
    JOINED -> AttributeManager_7
Template_for_Streetsurvey: AttributeManager
    ATTR_TABLE:
      RENAME_SET_VALUE jvid > JVID (int32) = FME_NULL_VALUE
      RENAME_SET_VALUE house_number > HNR_BASE (buffer)
      RENAME_SET_VALUE house_number_extension > HNR_FULL (buffer)
      RENAME_SET_VALUE bus_number > BUS_NR (buffer)
      SET_TO APPT_NR (varchar(200)) = FME_NULL_VALUE
      REMOVE jvid_use (varchar(255))
      REMOVE belmap_address_id (int32)
      RENAME_SET_VALUE belmap_building_id > BLDG_KEY (int32)
      RENAME_SET_VALUE street_name > STREET_NM (buffer)
      RENAME_SET_VALUE postal_code > PC (buffer)
      RENAME_SET_VALUE municipality > AXON_NAME (buffer)
      RENAME_SET_VALUE city > LAXON_NAME (buffer)
      RENAME_SET_VALUE x > X0 (real64)
      RENAME_SET_VALUE y > Y0 (real64)
      RENAME_SET_VALUE lat > LAT0 (real64)
      RENAME_SET_VALUE lon > LON0 (real64)
      SET_TO BLDG_TYPE (varchar(3)) = MDU
      SET_TO ADDR_KEY (varchar(200)) = FME_NULL_VALUE
AttributeManager_7
    ATTR_TABLE:
      SET_TO target_total (varchar(200)) = FME_CONDITIONAL:DEFAULT_VALUE'@Value(MDU_Total)'BOOL_OP;OR;COMPOSITE_TEST;1;TEST BG_ID ATTRIBUTE_HAS_A_VALUE _FME_BLANK_STRING_'@Value(BG_Total)'FME_NUM_CONDITIONS2___
      SET_TO bl_count (varchar(200)) = FME_CONDITIONAL:DEFAULT_VALUE'@Value(BL_MDU_Total)'BOOL_OP;OR;COMPOSITE_TEST;1;TEST BG_ID ATTRIBUTE_HAS_A_VALUE _FME_BLANK_STRING_'@Value(BL_BG_Total)'FME_NUM_CONDITIONS2___
      SET_TO tolerance (varchar(200)) = max(1, @mult(0.2, @Value(bl_count)))
Aggregator_3
    ACCUM_ATTRS = None
    AGGREGATE_TYPE = Homogeneous Collection (If Possible)
    COUNT_ATTR = Build List
    MODE = Geometry - Assemble One Level
    SEP = ,
    AGGREGATE -> AttributeManager_5
AttributeManager_5
    ATTR_TABLE:
      RENAME_SET_VALUE $(Area_ID) > Area_ID (varchar(200)) = $(Area_ID)
      RENAME_SET_VALUE $(DMP_Area_Area_ID) > DMP_Area_Area_ID (varchar(200)) = $(DMP_Area_Area_ID)
    USER_EXPOSED_ATTRIBUTES = $(Area_ID),$(DMP_Area_Area_ID)
    -> FeatureJoiner_8 [LEFT]
FeatureJoiner_8
    ATTR_CONFLICT_RES = USE_LEFT
    GEOMETRY_HANDLING = USE_LEFT
    JOIN_KEYS = DMP_Area_Area_ID area_id AUTO
    JOIN_MODE = Inner
    JOINED -> AttributeManager_6
    <REJECTED> -> FeatureJoiner_8__Rejected_
AttributeManager_6
    ATTR_TABLE:
      REMOVE id (int32)
      REMOVE contractor_id (int32)
      REMOVE created_at (datetime)
      REMOVE updated_at (datetime)
      REMOVE area_id (buffer)
      REMOVE import_id (int32)
      REMOVE area_released (logical)
      REMOVE region_name (buffer)
      REMOVE homes_passed_contractor_id (int32)
      REMOVE area_polygon_id (int32)
      REMOVE area_released_date (datetime)
      REMOVE pst_roll_out_end_date (datetime)
      REMOVE monday_board_id (buffer)
      REMOVE monday_group_id (buffer)
      REMOVE gf_project (varchar(255))
      REMOVE new_contractor_id (int32)
      REMOVE new_contractor_from (datetime)
      REMOVE ssv_contractor_id (int32)
    -> FeatureJoiner_7 [LEFT]
FeatureJoiner_7
    ATTR_CONFLICT_RES = USE_LEFT
    GEOMETRY_HANDLING = USE_LEFT
    JOIN_KEYS = DMP_Area_Area_ID DMP_Area_Area_ID AUTO
    JOIN_MODE = Inner
    JOINED -> FeatureWriter [Joined]
    UNJOINED_RIGHT -> FeatureWriter [Joined]
FeatureWriter [off]
    CONFIG_PARAMETERS = ESCAPE_COMMAS_IN_FTP_FORMAT_PARAMETERS,no
    DATASET = $(FME_MF_DIR_ENCODED)Outputs\BL-SSV deltas_v2.xlsx
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = No
    XLSXW_PROTECT_SHEET = NO
    XLSXW_RASTER_FORMAT = PNG
    XLSXW_STRICT_SCHEMA_ADDITIONAL_ATTRIBUTE_MATCHING = yes
    XLSXW_TRUNCATE_TABLE = No
    XLSXW_WRITER_MODE = Insert
FeatureJoiner_8__Rejected_: Inspector [off]

Bookmark: Inputs
MONDAY_ITEM_VIEW_GEOM (reader POSTGIS_1)
    attributes: item_id int8, task text, Doubles text, DMP AREA AREA ID text, DMP AREA NAME text, DMP POSTAL CODE text, DMP MUNICIPALITY text, DMP CITY text, DMP STREET text, DMP HOUSENUMBER text, DMP BUILDING KEY text, DMP BELMAP LU COUNT text, DMP POP AREA NAME text, DMP IN SCOPE text, APP SSV BLDG GRP INDIV TREATMENT text, APP SSV BLDG GRP MAIN ADDRESS text, APP SSV BU COUNT text, APP SSV BUILDING GROUP text, APP SSV BUILDING TYPE text, APP SSV DEPLOYMENT TYPE text, APP SSV LOW FLOOR text, APP SSV LU COUNT text, APP SSV QUADRANT text, APP SSV SU COUNT text, APP SSV TOTAL UNITS text, APP SSV UPPER FLOOR text, SSV ACTUAL DATE text, SSV COMPANY text, SSV AGENT text, SSV BLOCK text,
      SSV DOC LINK text, SSV PLANNED DATE text, SSV REGISTRATION STATUS text, SSV STATUS text, SSV SYNDIC text, SSV SYNDIC MAIL text, SSV SYNDIC NAME text, SSV SYNDIC PHONE text, SSV TIMESTAMP text, TSA 1ST REMINDER DATE text, TSA 2ND REMINDER DATE text, TSA 3RD REMINDER DATE text, TSA 4TH REMINDER DATE text, TSA DOC FOR SIGNATURE text, TSA DOC SIGNED text, TSA COMPANY text, TSA GENERAL ASSEMBLY DATE text, TSA NEGOTIATOR text, TSA NEGOTIATOR COMMENTS text, TSA READY TO SEND DATE text, TSA REFUSED DATE text, TSA REGISTRATION STATUS text, TSA SENT DATE text, TSA SIGNED DATE text, TSA STATUS text, ACT HP CY text, ACT HP CY DEADLINE text, ACT SSV CY text, ACT SSV DEADLINE text, ACT UNIFIBER text,
      ACT UNIFIBER DATE text, APP CCP SSV SU COUNT text, APP CHK SU COUNT text, APP PROCESSED text, BLD ALL READY STATUS text, BLD COMPANY text, BLD FIBER BLOWN ACTUAL DATE text, BLD FIBER BLOWN PLANNED DATE text, BLD FIBER BLOWN STATUS text, BLD FIBER SPLICED ACTUAL DATE text, BLD FIBER SPLICED PLANNED DATE text, BLD FIBER SPLICED STATUS text, BLD INTRO ACTUAL DATE text, BLD INTRO PLANNED DATE text, BLD INTRO STATUS text, BLD SSV USABILITY text, BLD VC ACTUAL DATE text, BLD VC PLANNED DATE text, BLD VC STATUS text, CCP CHECK DONE text, CCP SSV BU COUNT text, CCP SSV LOW FLOOR text, CCP SSV LU COUNT text, CCP SSV QUADRANT text, CCP SSV TOTAL UNITS text, CCP SSV UPPER FLOOR text, CHK SSV BU COUNT text, CHK SSV DOC LINK text, CHK SSV LU COUNT text, CHK SSV QUADRANT text,
      CHK SSV TOTAL UNITS text, CHK SSV UPPER FLOOR text, CHK TSA DOC FOR SIGNATURE text, CHK TSA DOC SIGNED text, CHK TSA STATUS text, PST CENTRAL POP STATUS text, PST DEL STAT CODE DESC text, PST DEL HCA text, PST HP ACTUAL DATE text, PST HP PLANNED DATE text, SSV VALIDATOR text, STS ACTUAL DATE text, STS DOC LINK text, STS PARTNER text, STS PLANNED DATE text, STS QUADRANT text, STS STATUS text, STS UNITS COUNT text, CCP cleanup scope text, CCP CLEANUP COMMENT text, Audit report text, Audit report date text, PRIORITY text, SSV VALIDATION STATUS text, VALIDATION COMMENT SSV text, SSV validation date text, SSV validation counter text, Picture Quality text, Cable/material trajectory text, Quadrant Design text,
      Contact Details text, Building Group Check text, SSV BLDG GRP MAIN ADDRESS CHK text, DMP LOCATION CHK text, SSV SU COUNT CHK text, SSV BU COUNT CHK text, SSV LU COUNT CHK text, SSV TOTAL UNITS CHK text, TSA VALIDATION STATUS text, VALIDATION COMMENT TSA text, TSA validation date text, TSA validation counter text, REWORK STATUS SSV text, REWORK STATUS TSA text, REFUSAL RESPONSIBILITY SSV text, REFUSAL RESPONSIBILITY TSA text, REFUSAL REASON SSV text, REFUSAL REASON TSA text, ACTION REQUIRED FROM SSV text, ACTION REQUIRED FROM TSA text
    -> Remove_comments_about_duplicates
address_scoping (reader POSTGIS_1) [off]
    attributes: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
address (reader POSTGIS_1)
    attributes: id serial,BTree, area_id int4,BTree, surveyed_by_id int4,BTree, created_at timestamp, updated_at timestamp, jvid int4,BTree, jvid_use varchar(255), belmap_address_id int4,BTree, belmap_building_id int4,BTree, street_name text,BTree, house_number text,BTree, house_number_extension text,BTree, bus_number text,BTree, appartment_number text, postal_code text,BTree, municipality text, building_type varchar(255),BTree, city text,BTree, x float8, y float8, home_released bool, home_released_date timestamp, survey_status varchar(255), survey_date timestamp, status varchar(255),BTree, service_type text, address_source varchar(255),BTree, delivery_status int4, reason_not_homes_passed int4, dwelling_unit_type varchar(255),
      building_use text, lot text, distribution_point_number text, dependency_of_others int4, homes_passed_plan_date timestamp, homes_passed_actual_date timestamp, civil_plan_date timestamp, installation_type varchar(255), length_estimate_from_street int4, existing_duct_frontyard text, lat float8, lon float8, amount_of_meters_dug int4, cocon_frame text, quadrant text, deleted_at timestamp, street_survey_distribution_way varchar(255), homes_connect_at timestamp, internal_remarks text, action_needed bool, capakey text, nis5 int4, nis9 text, preferred_distribution text, hc_type text, hc_length int4, num_floor int4, area_pop_id int4,BTree, central_pop_id int4,BTree, scopelist_v0 date,
      scopelist_v15 date, scopelist_v2 date, first_hp_wip date, first_hp_hca date, sub_address_of int4,BTree, belmap_version int4,BTree, home_release_blocked_at timestamp, home_release_blocked_reason varchar(255), main_address bool, fiberzone text, house_entry_deploy_type varchar(255), approved_for_release bool, home_release_reverted_at timestamp, quadrant_pst text, out_of_scope_at timestamp, ftu_location text, mdu_ssv text, quote_approved bool, pst_update_blocked bool, home_release_blocked_by_delay_id int4,BTree, batch text, building_group text, type text, distance_source text, pst_update_blocked_reason text, amount_of_meters_aerial int4, amount_of_meters_facade int4, homes_passed_wip_actual_date timestamp, ftu_floor int4, ftu_location_other text,
      ftu_other_room bool, excavation_above int4, quote_reference text, quote_required text, asphalt bool, twin_jvid int4, sdu_exceptional bool, meters_public int8, meters_private int8, meters_indoor int8, meters_existing_drop int8, quote_cost int8, rsn_trench text
    -> AttributeCreator_2
area (reader POSTGIS_1)
    attributes: id serial,PrimaryKey, contractor_id int4,BTREE, created_at timestamp, updated_at timestamp, area_name text,Unique, area_id text, import_id int4, area_released bool, region_name text, homes_passed_contractor_id int4, area_polygon_id int4,Unique, area_released_date timestamp, pst_roll_out_end_date timestamp, monday_board_id text, monday_group_id text, gf_project varchar(255), new_contractor_id int4,BTREE, new_contractor_from timestamp, ssv_contractor_id int4,BTREE
    -> FeatureJoiner_8 [RIGHT]

Bookmark: Apply validation results to SSV - Consolidated SSV input
Remove_comments_about_duplicates: TestFilter
    DEFAULT_VALUE = <UNFILTERED>
    PASSED_TEST_GROUP_OUTPUT = FIRST
    TEST_LIST:
      "BOOL_OP,OR,COMPOSITE_TEST,""""""1 OR 2"""""",TEST_CLAUSE,CASE_INSENSITIVE_TEST @Value(VALIDATION COMMENT SSV) CONTAINS uplicat
      CASE_INSENSITIVE_TEST @Value(VALIDATION COMMENT SSV) CONTAINS oublo",Duplicate,"BOOL_OP,COMPOSITE,COMPOSITE_TEST,""""""1 AND ( 2 OR ( NOT 3 AND 4 ))"""""",TEST_CLAUSE,TEST @Value(SSV STATUS) = NOT EXISTING
      TEST @sum(@Value(SSV BU COUNT CHK),@Value(SSV LU COUNT CHK)) = 0
      TEST SSV BU COUNT CHK ATTRIBUTE_HAS_A_VALUE ""
      TEST SSV LU COUNT CHK NOT_ATTRIBUTE_HAS_A_VALUE """,NOT EXISTING
    NOT EXISTING -> Set_0_for_not_existing
    <UNFILTERED> -> Update_values_by_validated_data
Set_0_for_not_existing: AttributeManager
    ATTR_TABLE:
      SET_TO APP SSV BU COUNT (buffer) = FME_CONDITIONAL:DEFAULT_VALUE'_FME_NO_OP_'BOOL_OP;COMPOSITE;COMPOSITE_TEST;1 AND ( 2 OR ( NOT 3 AND 4 ));TEST @Value(SSV STATUS) = NOT EXISTING;TEST @sum(@Value(SSV BU COUNT CHK),@Value(SSV LU COUNT CHK)) = 0;TEST SSV BU COUNT CHK ATTRIBUTE_HAS_A_VALUE _FME_BLANK_STRING_;TEST SSV LU COUNT CHK NOT_ATTRIBUTE_HAS_A_VALUE _FME_BLANK_STRING_'0'FME_NUM_CONDITIONS2___
      SET_TO APP SSV LU COUNT (buffer) = FME_CONDITIONAL:DEFAULT_VALUE'_FME_NO_OP_'BOOL_OP;COMPOSITE;COMPOSITE_TEST;1 AND ( 2 OR ( NOT 3 AND 4 ));TEST @Value(SSV STATUS) = NOT EXISTING;TEST @sum(@Value(SSV BU COUNT CHK),@Value(SSV LU COUNT CHK)) = 0;TEST SSV BU COUNT CHK ATTRIBUTE_HAS_A_VALUE _FME_BLANK_STRING_;TEST SSV LU COUNT CHK NOT_ATTRIBUTE_HAS_A_VALUE _FME_BLANK_STRING_'0'FME_NUM_CONDITIONS2___
      SET_TO APP SSV TOTAL UNITS (buffer) = FME_CONDITIONAL:DEFAULT_VALUE'_FME_NO_OP_'BOOL_OP;COMPOSITE;COMPOSITE_TEST;1 AND ( 2 OR ( NOT 3 AND 4 ));TEST @Value(SSV STATUS) = NOT EXISTING;TEST @sum(@Value(SSV BU COUNT CHK),@Value(SSV LU COUNT CHK)) = 0;TEST SSV BU COUNT CHK ATTRIBUTE_HAS_A_VALUE _FME_BLANK_STRING_;TEST SSV LU COUNT CHK NOT_ATTRIBUTE_HAS_A_VALUE _FME_BLANK_STRING_'0'FME_NUM_CONDITIONS2___
    -> Update_values_by_validated_data
Update_values_by_validated_data: AttributeManager
    ATTR_TABLE:
      SET_TO APP SSV BLDG GRP MAIN ADDRESS (buffer) = FME_CONDITIONAL:DEFAULT_VALUE'_FME_NO_OP_'BOOL_OP;OR;COMPOSITE_TEST;1;TEST SSV BLDG GRP MAIN ADDRESS CHK ATTRIBUTE_HAS_A_VALUE _FME_BLANK_STRING_'@Value(SSV BLDG GRP MAIN ADDRESS CHK)'FME_NUM_CONDITIONS2___
      SET_TO APP SSV BU COUNT (buffer) = FME_CONDITIONAL:DEFAULT_VALUE'_FME_NO_OP_'BOOL_OP;OR;COMPOSITE_TEST;1;TEST SSV BU COUNT CHK ATTRIBUTE_HAS_A_VALUE _FME_BLANK_STRING_'@Value(SSV BU COUNT CHK)'FME_NUM_CONDITIONS2___
      SET_TO APP SSV LU COUNT (buffer) = FME_CONDITIONAL:DEFAULT_VALUE'_FME_NO_OP_'BOOL_OP;OR;COMPOSITE_TEST;1;TEST SSV LU COUNT CHK ATTRIBUTE_HAS_A_VALUE _FME_BLANK_STRING_'@Value(SSV LU COUNT CHK)'FME_NUM_CONDITIONS2___
      SET_TO APP SSV TOTAL UNITS (buffer) = FME_CONDITIONAL:DEFAULT_VALUE'_FME_NO_OP_'BOOL_OP;OR;COMPOSITE_TEST;1;TEST SSV TOTAL UNITS CHK ATTRIBUTE_HAS_A_VALUE _FME_BLANK_STRING_'@Value(SSV TOTAL UNITS CHK)'FME_NUM_CONDITIONS2___
    -> Sort_by_address_-_validation_status_-_total_LU
Sort_by_address_-_validation_status_-_total_LU: Sorter
    SORT_PARM = DMP POSTAL CODE NATURAL ASCENDING NON_VALUES_BEFORE_VALUES DMP STREET NATURAL ASCENDING NON_VALUES_BEFORE_VALUES DMP HOUSENUMBER NATURAL ASCENDING NON_VALUES_BEFORE_VALUES SSV VALIDATION STATUS NATURAL DESCENDING NON_VALUES_AFTER_VALUES APP SSV TOTAL UNITS NATURAL DESCENDING NON_VALUES_AFTER_VALUES
    SORTED -> Remove_duplicate_MDU
Remove_duplicate_MDU: DuplicateFilter
    INPUT_ORDERED_CHOICE_LOOKUP = YES
    KEYATTR = DMP HOUSENUMBER DMP POSTAL CODE DMP STREET
    INPUT_ORDERED_CHOICE = Yes
    UNIQUE -> AttributeRemover
AttributeRemover
    REMOVE_ATTRS = ACT HP CY,ACT HP CY DEADLINE,ACT SSV CY,ACT SSV DEADLINE,ACT UNIFIBER,ACT UNIFIBER DATE,APP CCP SSV SU COUNT,APP CHK SU COUNT,APP PROCESSED,Audit report,Audit report date,BLD ALL READY STATUS,BLD COMPANY,BLD FIBER BLOWN ACTUAL DATE,BLD FIBER BLOWN PLANNED DATE,BLD FIBER BLOWN STATUS,BLD FIBER SPLICED ACTUAL DATE,BLD FIBER SPLICED PLANNED DATE,BLD FIBER SPLICED STATUS,BLD INTRO ACTUAL DATE,BLD INTRO PLANNED DATE,BLD INTRO STATUS,BLD SSV USABILITY,BLD VC ACTUAL DATE,BLD VC PLANNED DATE,BLD VC STATUS,Building Group Check,Cable/material trajectory,CCP CHECK DONE,CCP CLEANUP COMMENT,CCP cleanup scope,CCP SSV BU COUNT,CCP SSV LOW FLOOR,CCP SSV LU COUNT,CCP SSV QUADRANT,CCP SSV TOTAL UNITS,CCP SSV UPPER FLOOR,CHK SSV BU COUNT,CHK SSV DOC LINK,CHK SSV LU COUNT,CHK SSV QUADRANT,CHK SSV TOTAL UNITS,CHK SSV UPPER FLOOR,CHK TSA DOC FOR SIGNATURE,CHK TSA DOC SIGNED,CHK TSA STATUS,Contact Details,item_id,Picture Quality,PRIORITY,PST CENTRAL POP STATUS,PST DEL HCA,PST DEL STAT CODE DESC,PST HP ACTUAL DATE,PST HP PLANNED DATE,Quadrant Design,SSV ACTUAL DATE,SSV AGENT,SSV BLDG GRP MAIN ADDRESS CHK,SSV BLOCK,SSV BU COUNT CHK,SSV DOC LINK,SSV LU COUNT CHK,SSV PLANNED DATE,SSV REGISTRATION STATUS,SSV SU COUNT CHK,SSV SYNDIC,SSV SYNDIC MAIL,SSV SYNDIC NAME,SSV SYNDIC PHONE,SSV TIMESTAMP,SSV TOTAL UNITS CHK,SSV validation counter,SSV validation date,SSV VALIDATION STATUS,SSV VALIDATOR,STS ACTUAL DATE,STS DOC LINK,STS PARTNER,STS PLANNED DATE,STS QUADRANT,STS STATUS,STS UNITS COUNT,TSA 1ST REMINDER DATE,TSA 2ND REMINDER DATE,TSA 3RD REMINDER DATE,TSA 4TH REMINDER DATE,TSA DOC FOR SIGNATURE,TSA DOC SIGNED,TSA GENERAL ASSEMBLY DATE,TSA NEGOTIATOR,TSA NEGOTIATOR COMMENTS,TSA READY TO SEND DATE,TSA REFUSED DATE,TSA REGISTRATION STATUS,TSA SENT DATE,TSA SIGNED DATE,TSA STATUS,TSA validation counter,TSA validation date,TSA VALIDATION STATUS,VALIDATION COMMENT SSV,VALIDATION COMMENT TSA
    -> Counter
Counter
    CNT_ATTR = MDU_ID
    DOMAIN = counter
    SCOPE = Global
    START = 1
    -> AttributeManager
AttributeManager
    ATTR_TABLE:
      SET_TO MDU_ID (int64) = MDU_@Value(MDU_ID)
      SET_TO MDU_Total (varchar(200)) = @sum(@Value(APP SSV BU COUNT),@Value(APP SSV LU COUNT))
    -> TestFilter
    -> FeatureJoiner_9 [RIGHT]

Bookmark: Define BG ID
TestFilter
    DEFAULT_VALUE = <UNFILTERED>
    PASSED_TEST_GROUP_OUTPUT = FIRST
    TEST_LIST = "BOOL_OP,OR,COMPOSITE_TEST,""""""1"""""",TEST_CLAUSE,TEST APP SSV BLDG GRP MAIN ADDRESS ATTRIBUTE_HAS_A_VALUE """,APP SSV BLDG GRP MAIN ADDRESS ATTRIBUTE_HAS_A_VALUE
    APP SSV BLDG GRP MAIN ADDRESS ATTRIBUTE_HAS_A_VALUE -> FeatureJoiner [LEFT]
    APP SSV BLDG GRP MAIN ADDRESS ATTRIBUTE_HAS_A_VALUE -> FeatureJoiner_9 [LEFT]
    <UNFILTERED> -> FeatureJoiner_2 [RIGHT]
FeatureJoiner_9
    ATTR_CONFLICT_RES = USE_RIGHT
    GEOMETRY_HANDLING = USE_LEFT
    JOIN_KEYS = APP SSV BLDG GRP MAIN ADDRESS task AUTO
    JOIN_MODE = Inner
    JOINED -> DuplicateFilter
Counter_2
    CNT_ATTR = BG_ID
    DOMAIN = counter
    SCOPE = Global
    START = 1
    -> AttributeManager_2
AttributeManager_2
    ATTR_TABLE:
      REMOVE DMP AREA AREA ID (buffer)
      REMOVE DMP AREA NAME (buffer)
      REMOVE DMP POSTAL CODE (buffer)
      REMOVE DMP MUNICIPALITY (buffer)
      REMOVE DMP CITY (buffer)
      REMOVE DMP STREET (buffer)
      REMOVE DMP HOUSENUMBER (buffer)
      REMOVE DMP BUILDING KEY (buffer)
      REMOVE DMP BELMAP LU COUNT (buffer)
      REMOVE DMP POP AREA NAME (buffer)
      REMOVE DMP IN SCOPE (buffer)
      REMOVE APP SSV BLDG GRP INDIV TREATMENT (buffer)
      REMOVE APP SSV BLDG GRP MAIN ADDRESS (buffer)
      REMOVE APP SSV BU COUNT (buffer)
      REMOVE APP SSV BUILDING GROUP (buffer)
      REMOVE APP SSV BUILDING TYPE (buffer)
      REMOVE APP SSV DEPLOYMENT TYPE (buffer)
      REMOVE APP SSV LOW FLOOR (buffer)
      REMOVE APP SSV LU COUNT (buffer)
      REMOVE APP SSV QUADRANT (buffer)
      REMOVE APP SSV SU COUNT (buffer)
      REMOVE APP SSV TOTAL UNITS (buffer)
      REMOVE APP SSV UPPER FLOOR (buffer)
      REMOVE DMP LOCATION CHK (buffer)
      REMOVE Doubles (buffer)
      REMOVE SSV COMPANY (buffer)
      REMOVE TSA COMPANY (buffer)
      REMOVE REWORK STATUS SSV (buffer)
      REMOVE REWORK STATUS TSA (buffer)
      REMOVE REFUSAL RESPONSIBILITY SSV (buffer)
      REMOVE REFUSAL RESPONSIBILITY TSA (buffer)
      REMOVE REFUSAL REASON SSV (buffer)
      REMOVE REFUSAL REASON TSA (buffer)
      REMOVE ACTION REQUIRED FROM SSV (buffer)
      REMOVE ACTION REQUIRED FROM TSA (buffer)
      REMOVE SSV STATUS (buffer)
      SET_TO BG_ID (int64) = BG_@Value(BG_ID)
      REMOVE MDU_ID (int64)
      RENAME_SET_VALUE MDU_Total > BG_Total (varchar(200))
      RENAME_SET_VALUE task > APP SSV BLDG GRP MAIN ADDRESS (buffer)
    -> FeatureJoiner_2 [LEFT]
    -> FeatureJoiner [RIGHT]
    -> FeatureJoiner_5 [LEFT]
FeatureJoiner_2
    ATTR_CONFLICT_RES = USE_LEFT
    GEOMETRY_HANDLING = USE_LEFT
    JOIN_KEYS = APP SSV BLDG GRP MAIN ADDRESS task AUTO
    JOIN_MODE = Inner
    JOINED -> DuplicateFilter_2
    UNJOINED_RIGHT -> DuplicateFilter_2
FeatureJoiner
    ATTR_CONFLICT_RES = USE_LEFT
    GEOMETRY_HANDLING = USE_LEFT
    JOIN_KEYS = APP SSV BLDG GRP MAIN ADDRESS APP SSV BLDG GRP MAIN ADDRESS AUTO
    JOIN_MODE = Inner
    JOINED -> DuplicateFilter_2
    UNJOINED_RIGHT -> DuplicateFilter_2
DuplicateFilter_2
    INPUT_ORDERED_CHOICE_LOOKUP = NO
    KEYATTR = MDU_ID
    INPUT_ORDERED_CHOICE = No
    UNIQUE -> TestFilter_8
    UNIQUE -> FeatureJoiner_6 [LEFT]
TestFilter_8
    DEFAULT_VALUE = <UNFILTERED>
    PASSED_TEST_GROUP_OUTPUT = FIRST
    TEST_LIST = "BOOL_OP,OR,COMPOSITE_TEST,""""""1"""""",TEST_CLAUSE,TEST @Value(APP SSV BLDG GRP INDIV TREATMENT) = Yes",Indiv treatment
    <UNFILTERED> -> FeatureJoiner_5 [RIGHT]
FeatureJoiner_5
    ATTR_CONFLICT_RES = USE_LEFT
    GEOMETRY_HANDLING = USE_LEFT
    JOIN_KEYS = APP SSV BLDG GRP MAIN ADDRESS task AUTO
    JOIN_MODE = Inner
    JOINED -> AttributeManager_3
AttributeManager_3
    ATTR_TABLE = SET_TO BG_Total (varchar(200)) = @sum(@Value(APP SSV LU COUNT),@Value(APP SSV BU COUNT))
    -> AttributeRemover_2
AttributeRemover_2
    REMOVE_ATTRS = ACTION REQUIRED FROM SSV,ACTION REQUIRED FROM TSA,APP SSV BLDG GRP INDIV TREATMENT,APP SSV BLDG GRP MAIN ADDRESS,APP SSV BU COUNT,APP SSV BUILDING GROUP,APP SSV BUILDING TYPE,APP SSV DEPLOYMENT TYPE,APP SSV LOW FLOOR,APP SSV LU COUNT,APP SSV QUADRANT,APP SSV SU COUNT,APP SSV TOTAL UNITS,APP SSV UPPER FLOOR,DMP AREA AREA ID,DMP AREA NAME,DMP BELMAP LU COUNT,DMP BUILDING KEY,DMP CITY,DMP HOUSENUMBER,DMP IN SCOPE,DMP LOCATION CHK,DMP MUNICIPALITY,DMP POP AREA NAME,DMP POSTAL CODE,DMP STREET,Doubles,MDU_ID,MDU_Total,REFUSAL REASON SSV,REFUSAL REASON TSA,REFUSAL RESPONSIBILITY SSV,REFUSAL RESPONSIBILITY TSA,REWORK STATUS SSV,REWORK STATUS TSA,SSV COMPANY,SSV STATUS,task,TSA COMPANY
    -> FeatureJoiner_6 [RIGHT]
FeatureJoiner_6
    ATTR_CONFLICT_RES = USE_LEFT
    GEOMETRY_HANDLING = USE_LEFT
    JOIN_KEYS = BG_ID BG_ID AUTO
    JOIN_MODE = Inner
    JOINED -> BulkAttributeRenamer
    UNJOINED_LEFT -> BulkAttributeRenamer
    <REJECTED> -> FeatureJoiner_6__Rejected_
    <REJECTED> -> BulkAttributeRenamer
BulkAttributeRenamer
    ATTRCHOICE_ACTION = SELECTED
    ATTRLIST = ACTION REQUIRED FROM SSV ACTION REQUIRED FROM TSA APP SSV BLDG GRP INDIV TREATMENT APP SSV BLDG GRP MAIN ADDRESS APP SSV BU COUNT APP SSV BUILDING GROUP APP SSV BUILDING TYPE APP SSV DEPLOYMENT TYPE APP SSV LOW FLOOR APP SSV LU COUNT APP SSV SU COUNT APP SSV TOTAL UNITS APP SSV UPPER FLOOR DMP AREA AREA ID DMP AREA NAME DMP BELMAP LU COUNT DMP BUILDING KEY DMP CITY DMP HOUSENUMBER DMP IN SCOPE DMP LOCATION CHK DMP MUNICIPALITY DMP POP AREA NAME DMP POSTAL CODE DMP STREET Doubles REFUSAL REASON SSV REFUSAL REASON TSA REFUSAL RESPONSIBILITY SSV REFUSAL RESPONSIBILITY TSA REWORK STATUS SSV REWORK STATUS TSA SSV COMPANY SSV STATUS task TSA COMPANY
    MODE_CHOICE = RENAME
    PATTERN_ACTION_DISP = ADDPREFIX
    REPLACE_STR = SSV_
    ATTRCHOICE = Selected Attributes
    -> FeatureJoiner_3 [RIGHT]
    -> FeatureJoiner_4 [RIGHT]

Bookmark: Apply MDU ID - BG ID to JVID and BL total
AttributeCreator_2
    ATTR_TABLE = SET_TO Depl_type (varchar(200)) = @Left(@Value(delivery_status),1)
    INPUT_PORT_CONNECTED = CONNECTED
    -> BL-DL
BL-DL: TestFilter
    DEFAULT_VALUE = <UNFILTERED>
    PASSED_TEST_GROUP_OUTPUT = FIRST
    TEST_LIST:
      "BOOL_OP,AND,COMPOSITE_TEST,""""""1 AND 2"""""",TEST_CLAUSE,TEST scopelist_v2 ATTRIBUTE_HAS_A_VALUE ""
      TEST scopelist_v15 ATTRIBUTE_VALUE_NULL """,BL,"BOOL_OP,AND,COMPOSITE_TEST,""""""1 AND 2"""""",TEST_CLAUSE,TEST scopelist_v2 ATTRIBUTE_HAS_A_VALUE ""
      TEST scopelist_v15 ATTRIBUTE_HAS_A_VALUE """,BL-DL,"BOOL_OP,AND,COMPOSITE_TEST,""""""1 AND 2"""""",TEST_CLAUSE,TEST scopelist_v2 ATTRIBUTE_VALUE_NULL ""
      TEST scopelist_v15 ATTRIBUTE_HAS_A_VALUE """,DL,"BOOL_OP,AND,COMPOSITE_TEST,""""""1 AND 2"""""",TEST_CLAUSE,TEST scopelist_v2 ATTRIBUTE_VALUE_NULL ""
      TEST scopelist_v15 ATTRIBUTE_VALUE_NULL """,Out of scope
    BL -> FeatureJoiner_3 [LEFT]
    BL -> Aggregator_3
    BL-DL -> FeatureJoiner_3 [LEFT]
    BL-DL -> Aggregator_3
    DL -> In_scope_2
    Out of scope -> In_scope_2
FeatureJoiner_3
    ATTR_CONFLICT_RES = USE_LEFT
    GEOMETRY_HANDLING = USE_LEFT
    JOIN_KEYS = street_name SSV_DMP STREET AUTO house_number_extension SSV_DMP HOUSENUMBER AUTO postal_code SSV_DMP POSTAL CODE AUTO
    JOIN_MODE = Inner
    JOINED -> BulkAttributeRemover
    JOINED -> FeatureJoiner_10 [RIGHT]
    UNJOINED_LEFT -> FeatureJoiner_4 [LEFT]
BulkAttributeRemover
    ATTR_EXP = SSV_
    -> StatisticsCalculator
StatisticsCalculator
    ATTR_ACCUM_MODE = None
    CALCULATION_MODE = NUMERIC
    FEAT_STATS = jvid,NUMERIC_MODE,,,COUNT,,,,,,,,,,
    GROUP_BY = MDU_ID
    COMPLETE -> AttributeRenamer
AttributeRenamer
    ATTR_TABLE = RENAME_SET_DEFAULT jvid.total_count > BL_MDU_Total
    KEEP_RENAMED_ONLY = no
    MISSING_INPUT_ATTRS = REMOVE
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST BG_ID ATTRIBUTE_HAS_A_VALUE """,BG_ID ATTRIBUTE_HAS_A_VALUE
    BG_ID ATTRIBUTE_HAS_A_VALUE -> TestFilter_3
    <UNFILTERED> -> FeatureJoiner_4 [LEFT]
FeatureJoiner_4
    ATTR_CONFLICT_RES = USE_LEFT
    GEOMETRY_HANDLING = USE_LEFT
    JOIN_KEYS = building_group SSV_task AUTO
    JOIN_MODE = Inner
    JOINED -> BulkAttributeRemover_2
    UNJOINED_LEFT -> DuplicateFilter_3
    <REJECTED> -> FeatureJoiner_4__Rejected_
    <REJECTED> -> BulkAttributeRemover_3
BulkAttributeRemover_2
    ATTR_EXP = SSV_
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST BG_ID ATTRIBUTE_HAS_A_VALUE """,BG_ID ATTRIBUTE_HAS_A_VALUE
    BG_ID ATTRIBUTE_HAS_A_VALUE -> StatisticsCalculator_2
    <UNFILTERED> -> DuplicateFilter_3
StatisticsCalculator_2
    ATTR_ACCUM_MODE = None
    CALCULATION_MODE = NUMERIC
    FEAT_STATS = jvid,NUMERIC_MODE,,,COUNT,,,,,,,,,,
    GROUP_BY = BG_ID
    COMPLETE -> AttributeRenamer_2
AttributeRenamer_2
    ATTR_TABLE = RENAME_SET_DEFAULT jvid.total_count > BL_BG_Total
    KEEP_RENAMED_ONLY = no
    MISSING_INPUT_ATTRS = REMOVE
    -> DuplicateFilter_3
BulkAttributeRemover_3
    ATTR_EXP = SSV_
    -> DuplicateFilter_3
DuplicateFilter_3
    INPUT_ORDERED_CHOICE_LOOKUP = NO
    KEYATTR = jvid
    INPUT_ORDERED_CHOICE = No
    UNIQUE -> AttributeCreator
AttributeCreator
    ATTR_TABLE = SET_TO Delta (varchar(200)) = FME_CONDITIONAL:DEFAULT_VALUE'_FME_NO_OP_'BOOL_OP;OR;COMPOSITE_TEST;1;TEST BG_ID ATTRIBUTE_HAS_A_VALUE _FME_BLANK_STRING_'@sub(@Value(BG_Total),@Value(BL_BG_Total))'BOOL_OP;OR;COMPOSITE_TEST;1;TEST MDU_ID ATTRIBUTE_HAS_A_VALUE _FME_BLANK_STRING_'@sub(@Value(MDU_Total),@Value(BL_MDU_Total))'FME_NUM_CONDITIONS3___
    INPUT_PORT_CONNECTED = CONNECTED
    -> TestFilter_4
    -> AttributeCreator_3
    -> FeatureWriter_2 [Output]
    -> In_scope
FeatureJoiner_4__Rejected_: Inspector [off]

Bookmark: Feedback file
AttributeCreator_3 [off]
    ATTR_TABLE:
      SET_TO Initial (varchar(200)) = FME_CONDITIONAL:DEFAULT_VALUE'@Value(BL_MDU_Total)'BOOL_OP;OR;COMPOSITE_TEST;1;TEST BL_BG_Total ATTRIBUTE_HAS_A_VALUE _FME_BLANK_STRING_'@Value(BL_BG_Total)'FME_NUM_CONDITIONS2___
      SET_TO Target (varchar(200)) = FME_CONDITIONAL:DEFAULT_VALUE'@Value(MDU_Total)'BOOL_OP;OR;COMPOSITE_TEST;1;TEST BG_Total ATTRIBUTE_HAS_A_VALUE _FME_BLANK_STRING_'@Value(BG_Total)'FME_NUM_CONDITIONS2___
      SET_TO Type (varchar(200)) = FME_CONDITIONAL:DEFAULT_VALUE'_FME_NO_OP_'BOOL_OP;OR;COMPOSITE_TEST;1;TEST delivery_status ATTRIBUTE_IS_MISSING _FME_BLANK_STRING_'New MDU'BOOL_OP;COMPOSITE;COMPOSITE_TEST;( 1 OR 2 OR 3 OR 4 OR 5 ) AND ( 6 );TEST @Value(APP SSV QUADRANT) = A;TEST @Value(APP SSV QUADRANT) = Ax;TEST @Value(APP SSV QUADRANT) = C;TEST @Value(APP SSV QUADRANT) = Cx;TEST @Value(APP SSV QUADRANT) = Dx;TEST @Value(Initial) = 1'SDU to MDU in Q Dx,C,Cx,A,Ax'BOOL_OP;AND;COMPOSITE_TEST;1 AND 2 AND 3;TEST @Value(APP SSV QUADRANT) = D;TEST @Value(Initial) = 1;TEST @Value(Target) <= 4'SDU to MDU in QD - Spare'BOOL_OP;AND;COMPOSITE_TEST;1 AND 2 AND 3;TEST @Value(APP SSV QUADRANT) = D;TEST @Value(Initial) = 1;TEST @Value(Target) > 4'SDU to MDU in QD - no Spare'BOOL_OP;COMPOSITE;COMPOSITE_TEST;1 OR 2 AND ( 3 );TEST @Value(APP SSV QUADRANT) = M;TEST @Value(APP SSV QUADRANT) = P;TEST @Value(Initial) = 1'QM and QP'BOOL_OP;COMPOSITE;COMPOSITE_TEST;( 1 OR 2 OR 3 OR 4 ) AND 5 AND 6 AND 7;TEST @Value(APP SSV QUADRANT) = A;TEST @Value(APP SSV QUADRANT) = Ax;TEST @Value(APP SSV QUADRANT) = C;TEST @Value(APP SSV QUADRANT) = Cx;TEST @Value(Initial) > 1;TEST @Left(@Value(delivery_status),1) = 7;TEST @Evaluate(@sub(@Value(Target),@Value(Initial))) <= @max(1,@mult(0.2,@Value(Initial)))'Q C,Cx,A,Ax - UG Distribution -  spare'BOOL_OP;COMPOSITE;COMPOSITE_TEST;( 1 OR 2 OR 3 OR 4 ) AND 5 AND 6 AND 7;TEST @Value(APP SSV QUADRANT) = A;TEST @Value(APP SSV QUADRANT) = Ax;TEST @Value(APP SSV QUADRANT) = C;TEST @Value(APP SSV QUADRANT) = Cx;TEST @Value(Initial) > 1;TEST @Left(@Value(delivery_status),1) = 7;TEST @Evaluate(@sub(@Value(Target),@Value(Initial))) > @max(1,@mult(0.2,@Value(Initial)))'Q C,Cx,A,Ax - UG Distribution - no spare'BOOL_OP;COMPOSITE;COMPOSITE_TEST;( 1 OR 2 OR 3 OR 4 ) AND 5 AND 6;TEST @Value(APP SSV QUADRANT) = A;TEST @Value(APP SSV QUADRANT) = Ax;TEST @Value(APP SSV QUADRANT) = C;TEST @Value(APP SSV QUADRANT) = Cx;TEST @Value(Initial) > 1;TEST @Left(@Value(delivery_status),1) = 8'Q C,Cx,A,Ax - Facade Distribution 'BOOL_OP;COMPOSITE;COMPOSITE_TEST;( 1 OR 2 OR 3 OR 4 ) AND 5 AND 6 AND 7;TEST @Value(APP SSV QUADRANT) = A;TEST @Value(APP SSV QUADRANT) = Ax;TEST @Value(APP SSV QUADRANT) = C;TEST @Value(APP SSV QUADRANT) = Cx;TEST Initial$ > 1;TEST @Left(@Value(delivery_status),1) = 9;TEST @Evaluate(@sub(@Value(Target),@Value(Initial))) <= @max(1,@mult(0.2,@Value(Initial)))'Q C,Cx,A,Ax - Aerial Distribution - Spare'BOOL_OP;COMPOSITE;COMPOSITE_TEST;( 1 OR 2 OR 3 OR 4 ) AND 5 AND 6 AND 7;TEST @Value(APP SSV QUADRANT) = A;TEST @Value(APP SSV QUADRANT) = Ax;TEST @Value(APP SSV QUADRANT) = C;TEST @Value(APP SSV QUADRANT) = Cx;TEST @Value(Initial) > 1;TEST @Left(@Value(delivery_status),1) = 9;TEST @Evaluate(@sub(@Value(Target),@Value(Initial))) > @max(1,@mult(0.2,@Value(Initial)))'Q C,Cx,A,Ax - Aerial Distribution - no Spare'BOOL_OP;COMPOSITE;COMPOSITE_TEST;( 1 OR 2 ) AND 3 AND 4;TEST @Value(APP SSV QUADRANT) = D;TEST @Value(APP SSV QUADRANT) = Dx;TEST @Value(Initial) > 1;TEST @Value(Target) <= @mult(@add(@round(@div(@Value(Initial),4),0),1),4)'Q D,Dx - Spare'BOOL_OP;COMPOSITE;COMPOSITE_TEST;( 1 OR 2 ) AND 3 AND 4;TEST @Value(APP SSV QUADRANT) = D;TEST @Value(APP SSV QUADRANT) = Dx;TEST @Value(Initial) > 1;TEST @Value(Target) > @mult(@add(@round(@div(@Value(Initial),4),0),1),4)'Q D,Dx - no Spare'BOOL_OP;OR;COMPOSITE_TEST;1;TEST APP SSV QUADRANT NOT_ATTRIBUTE_HAS_A_VALUE _FME_BLANK_STRING_'No SSV'FME_NUM_CONDITIONS14___
    INPUT_PORT_CONNECTED = CONNECTED
    -> TestFilter_6 [off]
TestFilter_6 [off]
    DEFAULT_VALUE = <UNFILTERED>
    PASSED_TEST_GROUP_OUTPUT = FIRST
    TEST_LIST:
      "BOOL_OP,OR,COMPOSITE_TEST,""""""1 OR 2"""""",TEST_CLAUSE,TEST @Value(Delta) = 0
      TEST Delta ATTRIBUTE_VALUE_NULL """,Delta =0,"BOOL_OP,OR,COMPOSITE_TEST,""""""1"""""",TEST_CLAUSE,TEST BG_ID ATTRIBUTE_HAS_A_VALUE """,BG ID
    BG ID -> Aggregator [off]
    <UNFILTERED> -> TestFilter_7 [off]
Aggregator [off]
    ACCUM_ATTRS = None
    AGGREGATE_TYPE = Homogeneous Collection (If Possible)
    CONCAT_ATTRS = delivery_status bus_number jvid
    GROUP_BY = BG_ID Delta BG_Total BL_BG_Total Type
    MODE = Geometry - Assemble One Level
    SEP = ,
    AGGREGATE -> PythonCaller [off]
TestFilter_7 [off]
    DEFAULT_VALUE = <UNFILTERED>
    PASSED_TEST_GROUP_OUTPUT = FIRST
    TEST_LIST = "BOOL_OP,OR,COMPOSITE_TEST,""""""1"""""",TEST_CLAUSE,TEST MDU_ID ATTRIBUTE_HAS_A_VALUE """,MDU ID
    MDU ID -> Aggregator_2 [off]
Aggregator_2 [off]
    ACCUM_ATTRS = None
    AGGREGATE_TYPE = Homogeneous Collection (If Possible)
    CONCAT_ATTRS = delivery_status bus_number jvid status
    GROUP_BY = MDU_ID Delta BL_MDU_Total MDU_Total Type
    MODE = Geometry - Assemble One Level
    SEP = ,
    AGGREGATE -> PythonCaller [off]
PythonCaller [off]
    INPUT_PORT_CONNECTED = *
    NEW_ATTRIBUTES = LU_ACTION varchar(20) final_action varchar(20) action_reason varchar(200) type varchar(10) lu_count_bl int32 lu_count_ssv int32 feedback varchar(200) jvid varchar(20) bus_number varchar(20) status varchar(20) delivery_status varchar(20) group_scope varchar(20) group_id varchar(20) upstream_type varchar(20)
    PYTHONSOURCE:
      # -*- coding: utf-8 -*-
      """
      LU Reconciliation PythonCaller for BL-DL-SSV_Rework_v1.fmw.

      Two specs govern this code:
        1. lu_reconciliation_requirements.md
           Per-LU action (KEEP / REMOVE / ADD), bus_number outlier detection,
           bus_number sequence suggestion, HOMES_CONNECT lock.
        2. SSV review requirements
           Per-address final_action (Keep / Add / Remove / Modify / Review)
           with action_reason, type (MDU/SDU), lu_count_bl, lu_count_ssv.

      Input (from FMW v1 — two Aggregator transformers):

        Path A — BG-level (Aggregator):
          Group-By : BG_ID, Delta, BG_Total, BL_BG_Total, Type
          Concat   : delivery_status, bus_number, jvid  (comma-separated, aligned)

        Path B — MDU-level (Aggregator_2):
          Group-By : MDU_ID, Delta, BL_MDU_Total, MDU_Total, Type
          Concat   : delivery_status, bus_number, jvid, status  (comma-separated)

        Path C — Delta=0 / no-change (connect TestFilter_6 "Delta =0" here):
          Same attributes; Delta is 0 or null. These produce final_action = Keep.

        target   = BG_Total  (A) or MDU_Total  (B)   — SSV LU count
        count_dl = BL_BG_Total (A) or BL_MDU_Total (B) — BL LU count

      Output: one FME feature per LU.

      FME: Class FeatureProcessor, Symbol FeatureProcessor.
           FME 2024.2, Python 3.12.
      """

      from __future__ import annotations

      import json
      import os
      import re
      import ssl
      import urllib.error
      import urllib.request
      from collections import Counter

      import fmeobjects


      # ───────────────────────────────────────────────────────────────────────────
      # Ollama helpers (optional enrichment — stdlib only)
      # ───────────────────────────────────────────────────────────────────────────

      def _ollama_enabled():
          return os.environ.get("OLLAMA_ENABLED", "1").strip() not in ("0", "false", "no", "")

      def _ollama_host():
          return os.environ.get("OLLAMA_HOST", "http://127.0.0.1:11434").rstrip("/")

      def _ollama_model():
          return os.environ.get("OLLAMA_MODEL", "llama3.2").strip()

      def _ollama_timeout():
          try:
              return int(os.environ.get("OLLAMA_TIMEOUT", "120"))
          except ValueError:
              return 120

      def _ollama_chat(messages, *, model=None):
          host = _ollama_host()
          m = model or _ollama_model()
          data = json.dumps({
              "model": m, "messages": messages,
              "stream": False, "options": {"temperature": 0.1},
          }).encode()
          req = urllib.request.Request(
              f"{host}/api/chat", data=data,
              headers={"Content-Type": "application/json"}, method="POST",
          )
          ctx = ssl.create_default_context()
          with urllib.request.urlopen(req, timeout=_ollama_timeout(), context=ctx) as resp:
              body = json.loads(resp.read().decode())
          return str(body.get("message", {}).get("content", "")).strip()

      def _enrich_feedback_ollama(lu_rows, *, group_id, target, count_dl, ctx_attrs):
          """Mutate lu_rows[*]['feedback'] in place via Ollama. Fails silently."""
          if not _ollama_enabled() or not lu_rows:
              return
          lines = [
              f"{i}<pipe>jvid={r.get('jvid','')!r}<pipe>bus={r.get('bus_number','')!r}<pipe>"
              f"action={r.get('action','')!r}<pipe>feedback={r.get('feedback','')!r}"
              for i, r in enumerate(lu_rows)
          ]
          ctx_blob = "\n".join(f"{k}={v!r}" for k, v in sorted(ctx_attrs.items()) if v)
          system = (
              "You help Belgian fiber LU reconciliation. Output ONLY valid JSON. "
              'Schema: {"notes": ["...", ...]} — one string per row. '
              "Each note: max 25 words, explains how totals relate to this LU. "
              "Empty string if nothing to add. Never contradict the action."
          )
          user = (
              f"Group={group_id!r} target_LU={target} current_count={count_dl}.\n"
              f"Context:\n{ctx_blob or '(none)'}\nRows:\n" + "\n".join(lines)
          )
          try:
              raw = _ollama_chat([
                  {"role": "system", "content": system},
                  {"role": "user", "content": user},
              ])
              m = re.search(r"\{[\s\S]*\}", raw.strip())
              if not m:
                  return
              parsed = json.loads(m.group(0))
              notes = parsed.get("notes")
              if not isinstance(notes, list) or len(notes) != len(lu_rows):
                  return
              for lu, note in zip(lu_rows, notes):
                  n = str(note).strip() if note else ""
                  if n:
                      base = (lu.get("feedback") or "").strip()
                      lu["feedback"] = f"{base} [{n}]" if base else n
          except (urllib.error.URLError, urllib.error.HTTPError,
                  TimeoutError, OSError, json.JSONDecodeError, ValueError):
              return


      # ───────────────────────────────────────────────────────────────────────────
      # Parsing helpers
      # ───────────────────────────────────────────────────────────────────────────

      def _get_attr(feature, name):
          try:
              v = feature.getAttribute(name)
          except Exception:
              v = None
          if v is None:
              return None
          s = str(v).strip()
          return s if s not in ("", "None") else None

      def _safe_int(val, default=0):
          try:
              return int(float(str(val)))
          except (ValueError, TypeError):
              return default

      def _split_csv(val):
          """Split Aggregator comma-concat; keep empty tokens for column alignment."""
          if val is None or str(val).strip() == "":
              return []
          return [p.strip() for p in str(val).split(",")]

      def _pad(lst, n):
          return lst + [""] * (n - len(lst))

      def _parse_aggregator(jvid_val, bus_val, delivery_val, status_val=None):
          """Parse comma-concatenated Aggregator fields into aligned per-LU lists."""
          jv = _split_csv(jvid_val)
          bn = _split_csv(bus_val)
          ds = _split_csv(delivery_val)
          st = _split_csv(status_val) if status_val is not None else []
          n = max(len(jv), len(bn), len(ds), len(st), 1)
          return _pad(jv, n), _pad(bn, n), _pad(ds, n), _pad(st, n), n


      # ───────────────────────────────────────────────────────────────────────────
      # Bus-number logic (lu_reconciliation_requirements.md)
      # ───────────────────────────────────────────────────────────────────────────

      def _parse_busnum(bn):
          """Parse 'A101' → ('A', '101', 101) or None."""
          if not bn:
              return None
          m = re.fullmatch(r"([A-Za-z]*)(\d+)", bn.strip())
          if m:
              return m.group(1).upper(), m.group(2), int(m.group(2))
          return None

      def _sort_key(bn):
          if not bn or not bn.strip():
              return (2, "", 0, "")
          p = _parse_busnum(bn.strip())
          if p:
              return (0, p[0], p[2], "")
          return (1, "", 0, bn.strip().lower())

      def _normalize_busnum(bn):
          if not bn:
              return ""
          s = bn.strip().lower()
          for pfx in ("bte", "box", "apt", "app", "flat", "unit"):
              if s.startswith(pfx):
                  s = s[len(pfx):]
                  break
          return s.lstrip("0") or "0"

      def detect_outliers(bus_numbers):
          """Return set of indices that are outliers among bus_numbers."""
          outlier_idx = set()
          parsed = [_parse_busnum(bn) if bn and bn.strip() else None for bn in bus_numbers]
          prefixes = [p[0] for p in parsed if p is not None]
          if not prefixes:
              return outlier_idx

          prefix_counts = Counter(prefixes)
          dominant_prefix, dom_count = prefix_counts.most_common(1)[0]

          # Flag non-dominant prefixes
          if dom_count > 1:
              for i, p in enumerate(parsed):
                  if p is not None and p[0] != dominant_prefix:
                      outlier_idx.add(i)

          # Within dominant prefix group: flag wrong digit lengths
          dom_group = [i for i, p in enumerate(parsed)
                       if p is not None and p[0] == dominant_prefix and i not in outlier_idx]
          dominant_dl = None
          if dom_group:
              nums = [parsed[i][2] for i in dom_group]
              range_spans_boundary = len(str(min(nums))) != len(str(max(nums)))
              dl_counts = Counter(len(parsed[i][1]) for i in dom_group)
              dominant_dl = dl_counts.most_common(1)[0][0]
              if not range_spans_boundary and dl_counts.most_common(1)[0][1] > 1:
                  for i in dom_group:
                      if len(parsed[i][1]) != dominant_dl:
                          outlier_idx.add(i)

          # Duplicate normalisation
          norm_map = {}
          for i, bn in enumerate(bus_numbers):
              if i in outlier_idx or not bn or not bn.strip():
                  continue
              norm = _normalize_busnum(bn)
              if norm in norm_map:
                  other = norm_map[norm]
                  def _is_dom(p):
                      if p is None:
                          return False
                      ok = p[0] == dominant_prefix
                      if dominant_dl is not None:
                          ok = ok and len(p[1]) == dominant_dl
                      return ok
                  if _is_dom(parsed[i]) and not _is_dom(parsed[other]):
                      outlier_idx.add(other)
                      norm_map[norm] = i
                  else:
                      outlier_idx.add(i)
              else:
                  norm_map[norm] = i

          return outlier_idx

      def suggest_bus_numbers(existing, n_add):
          """Suggest n_add new bus_numbers following the dominant pattern."""
          if n_add <= 0:
              return []
          clean = [b for b in existing if b and b.strip()]
          outliers = detect_outliers(clean)
          pool = [b for i, b in enumerate(clean) if i not in outliers]
          parsed_pool = [p for p in (_parse_busnum(b) for b in pool) if p is not None]
          used = set(b.strip() for b in clean)

          if not parsed_pool:
              sugg, c = [], 1
              while len(sugg) < n_add:
                  if str(c) not in used:
                      sugg.append(str(c))
                  c += 1
              return sugg

          prefix_counts = Counter(p[0] for p in parsed_pool)
          dom_prefix = prefix_counts.most_common(1)[0][0]
          dom_parsed = [p for p in parsed_pool if p[0] == dom_prefix]
          dl_counts = Counter(len(p[1]) for p in dom_parsed)
          pad_len = dl_counts.most_common(1)[0][0]
          nums = [p[2] for p in dom_parsed]

          if len(nums) == 1:
              sugg, nv = [], nums[0] + 1
              while len(sugg) < n_add:
                  c = dom_prefix + str(nv).zfill(pad_len)
                  if c not in used:
                      sugg.append(c)
                  nv += 1
              return sugg

          padded = [str(v).zfill(pad_len) for v in nums]
          pos_vals = [set(s[pos] for s in padded) for pos in range(pad_len)]
          varying = [i for i, vs in enumerate(pos_vals) if len(vs) > 1]
          fixed = {i: list(vs)[0] for i, vs in enumerate(pos_vals) if len(vs) == 1}

          if not varying:
              sugg, nv = [], max(nums) + 1
              while len(sugg) < n_add:
                  c = dom_prefix + str(nv).zfill(pad_len)
                  if c not in used:
                      sugg.append(c)
                  nv += 1
              return sugg

          floor_pos = varying[0]
          inner = varying[1:]
          floor_vals = sorted(set(int(s[floor_pos]) for s in padded))
          max_floor = max(floor_vals)
          inner_combos = sorted(set(
              tuple(s[p] for p in inner) for s in padded
          )) if inner else [()]

          sugg = []
          nf = max_floor + 1
          while len(sugg) < n_add and nf <= 99:
              for combo in inner_combos:
                  if len(sugg) >= n_add:
                      break
                  chars = ["0"] * pad_len
                  for p, d in fixed.items():
                      chars[p] = d
                  chars[floor_pos] = str(nf)
                  for p, d in zip(inner, combo):
                      chars[p] = d
                  c = dom_prefix + "".join(chars)
                  if c not in used:
                      sugg.append(c)
                      used.add(c)
              nf += 1

          # Fallback: simple increment
          if len(sugg) < n_add:
              nv = max(nums) + 1
              while len(sugg) < n_add:
                  c = dom_prefix + str(nv).zfill(pad_len)
                  if c not in used:
                      sugg.append(c)
                      used.add(c)
                  nv += 1
          return sugg


      # ───────────────────────────────────────────────────────────────────────────
      # SSV review: final_action per address (SSV review requirements)
      # ───────────────────────────────────────────────────────────────────────────

      def _determine_final_action(target, count_dl, delta):
          """
          Business rules → (final_action, action_reason, address_type).

          Rule 3: target=0, count_dl>0  → Remove
          Rule 4: count_dl=0, target>0  → Add   (Review requires upstream polygon flag)
          Rule 1: count_dl=1, target=1  → Modify (MDU→SDU)
          Rule 1: count_dl=1, target>1  → Modify (add LUs)
          Rule 2: count_dl>1, delta!=0  → Modify (LU count adjustment)
          Rule 5: delta=0               → Keep
          """
          # Rule 3 — not existing / empty
          if target == 0 and count_dl > 0:
              t = "MDU" if count_dl > 1 else "SDU"
              return ("Remove",
                      "SSV status not existing or empty — flagged for removal",
                      t)

          # Rule 4 — net new (in SSV, not in BL)
          if count_dl == 0 and target > 0:
              t = "MDU" if target > 1 else "SDU"
              return ("Add",
                      "Net new address from SSV, not present in Build List",
                      t)

          # Rule 1a — MDU with 1 LU, SSV confirms 1 → convert to SDU
          if count_dl == 1 and target == 1:
              return ("Modify",
                      "MDU with 1 LU: SSV confirms 1 unit — convert to SDU, bus_number to NULL",
                      "SDU")

          # Rule 1b / Rule 2 — count mismatch
          if delta != 0:
              t = "MDU" if target > 1 else "SDU"
              if delta > 0:
                  return ("Modify",
                          f"LU count adjustment: add {delta} LU(s) (BL={count_dl}, SSV={target})",
                          t)
              else:
                  return ("Modify",
                          f"LU count adjustment: remove {abs(delta)} LU(s) (BL={count_dl}, SSV={target})",
                          t)

          # Rule 5 — no change
          t = "MDU" if count_dl > 1 else "SDU"
          return ("Keep",
                  "No change: SSV confirms existing status and count",
                  t)


      # ───────────────────────────────────────────────────────────────────────────
      # Core per-group reconciliation
      # ───────────────────────────────────────────────────────────────────────────

      def reconcile_group(group):
          """
          Takes a parsed group dict, returns list of per-LU result dicts.

          Each result has:
            LU-level  : action (KEEP/REMOVE/ADD), feedback, jvid, bus_number,
                        status, delivery_status
            Address   : final_action, action_reason, type, lu_count_bl, lu_count_ssv
          """
          target = group["target"]
          count_dl = group["count_dl"]
          delta = target - count_dl
          jvids = group["jvids"]
          bus_numbers = group["bus_numbers"]
          statuses = group["statuses"]
          delivery_statuses = group["delivery_statuses"]
          n_lu = group["n_lu"]

          final_action, action_reason, addr_type = _determine_final_action(
              target, count_dl, delta)

          # Build per-LU rows (existing LUs)
          lus = []
          for i in range(n_lu):
              lus.append({
                  "jvid": jvids[i],
                  "bus_number": bus_numbers[i],
                  "status": statuses[i],
                  "delivery_status": delivery_statuses[i],
                  "action": "KEEP",
                  "feedback": "",
              })

          # ── Pre-existing duplicate warning ──
          bn_count = Counter(lu["bus_number"] for lu in lus if lu["bus_number"])
          for lu in lus:
              bn = lu["bus_number"]
              if bn and bn_count[bn] > 1:
                  lu["feedback"] = f"Warning: duplicate bus_number ({bn}) in source data"

          # ── Special: MDU→SDU conversion (Rule 1a) ──
          if final_action == "Modify" and addr_type == "SDU" and count_dl == 1 and target == 1:
              for lu in lus:
                  lu["action"] = "KEEP"
                  lu["bus_number"] = ""
                  lu["feedback"] = "Modify: MDU converted to SDU, bus_number set to NULL"
              return _attach_address_fields(lus, final_action, action_reason,
                                             addr_type, count_dl, target, group)

          n_remove = max(n_lu - target, 0)
          n_add = max(target - n_lu, 0)

          # ── No change ──
          if n_remove == 0 and n_add == 0:
              return _attach_address_fields(lus, final_action, action_reason,
                                             addr_type, count_dl, target, group)

          # ── REMOVE logic ──
          if n_remove > 0:
              locked = [False] * n_lu

              # Lock HOMES_CONNECT
              for i, lu in enumerate(lus):
                  if (lu["status"] or "").strip().upper() == "HOMES_CONNECT":
                      locked[i] = True

              # Lock NULL bus_number when MDU→SDU (target=1)
              if target == 1:
                  for i, lu in enumerate(lus):
                      if not lu["bus_number"]:
                          locked[i] = True
                          lu["feedback"] = "Kept: NULL bus_number retained (MDU becoming SDU)"
                          break

              unlocked = [i for i in range(n_lu) if not locked[i]]

              # Check if delivery_statuses are uniform across unlocked
              unlocked_ds = set(
                  str(lus[i]["delivery_status"]) if lus[i]["delivery_status"] else ""
                  for i in unlocked
              )
              ds_uniform = len(unlocked_ds) <= 1

              # Candidate flagging
              unlocked_bns = [lus[i]["bus_number"] for i in unlocked]
              outlier_set = {unlocked[j] for j in detect_outliers(unlocked_bns)}
              seen_bn = {}
              cand_flags = {i: [] for i in unlocked}

              for i in unlocked:
                  lu = lus[i]
                  ds = str(lu["delivery_status"]) if lu["delivery_status"] else ""
                  bn = lu["bus_number"]

                  # Status-based flags only when statuses differ
                  if not ds_uniform:
                      if ds and ds.startswith("2"):
                          cand_flags[i].append("delivery_status starts with 2")
                      if ds and not ds.endswith("5"):
                          cand_flags[i].append("delivery_status not ending with 5")

                  if not bn and len(unlocked) > 1:
                      cand_flags[i].append("bus_number is empty/null")
                  if i in outlier_set:
                      cand_flags[i].append(f"bus_number outlier ({bn})")
                  if bn:
                      if bn in seen_bn:
                          cand_flags[i].append(f"duplicate bus_number ({bn})")
                      else:
                          seen_bn[bn] = i

              candidates = sorted(
                  [i for i in unlocked if cand_flags[i]],
                  key=lambda i: _sort_key(lus[i]["bus_number"]))
              non_candidates = sorted(
                  [i for i in unlocked if not cand_flags[i]],
                  key=lambda i: _sort_key(lus[i]["bus_number"]))

              to_remove = set()
              remaining = n_remove
              while remaining > 0 and candidates:
                  to_remove.add(candidates.pop())
                  remaining -= 1
              while remaining > 0 and non_candidates:
                  to_remove.add(non_candidates.pop())
                  remaining -= 1

              for i in unlocked:
                  lu = lus[i]
                  if i in to_remove:
                      flags = cand_flags[i]
                      lu["action"] = "REMOVE"
                      lu["feedback"] = ("Remove: " + ", ".join(flags)) if flags else \
                          "Remove: removed from end (no candidate flags)"
                  elif cand_flags[i]:
                      lu["feedback"] = "Kept (candidate but not needed): " + \
                          ", ".join(cand_flags[i])

          # ── ADD logic ──
          if n_add > 0:
              existing_bns = [lu["bus_number"] for lu in lus]
              suggestions = suggest_bus_numbers(existing_bns, n_add)
              for k in range(n_add):
                  suggested = suggestions[k] if k < len(suggestions) else ""
                  lus.append({
                      "jvid": "",
                      "bus_number": suggested,
                      "status": "",
                      "delivery_status": "",
                      "action": "ADD",
                      "feedback": f"New LU — suggested bus_number: {suggested}",
                  })

          return _attach_address_fields(lus, final_action, action_reason,
                                         addr_type, count_dl, target, group)


      def _attach_address_fields(lus, final_action, action_reason,
                                  addr_type, count_dl, target, group):
          """Stamp address-level SSV review fields onto every LU row."""
          for lu in lus:
              lu["final_action"] = final_action
              lu["action_reason"] = action_reason
              lu["type"] = addr_type
              lu["lu_count_bl"] = count_dl
              lu["lu_count_ssv"] = target
              lu["group_scope"] = group["group_scope"]
              lu["group_id"] = group["group_id"]
              lu["upstream_type"] = group.get("upstream_type", "")
              lu["delta"] = group["delta"]
          return lus


      # ───────────────────────────────────────────────────────────────────────────
      # FME FeatureProcessor
      # ───────────────────────────────────────────────────────────────────────────

      class FeatureProcessor(object):
          def __init__(self):
              self._groups = []

          def input(self, feature):
              ga = lambda name: _get_attr(feature, name)

              md_id = ga("MDU_ID")
              bg_id = ga("BG_ID")

              # ── Determine scope and extract counts ──
              # Only two input paths exist in v1:
              #   Aggregator  (BG):  GROUP_BY BG_ID, Delta, BG_Total, BL_BG_Total, Type
              #   Aggregator_2(MDU): GROUP_BY MDU_ID, Delta, BL_MDU_Total, MDU_Total, Type
              if md_id:
                  group_scope = "MDU"
                  group_id = md_id
                  target = _safe_int(ga("MDU_Total"), 0)
                  count_dl = _safe_int(ga("BL_MDU_Total"), 0)
              elif bg_id:
                  group_scope = "BG"
                  group_id = bg_id
                  target = _safe_int(ga("BG_Total"), 0)
                  count_dl = _safe_int(ga("BL_BG_Total"), 0)
              else:
                  # Should not happen in v1 flow — log and skip
                  return

              jvids, bns, ds, sts, n_lu = _parse_aggregator(
                  ga("jvid"), ga("bus_number"), ga("delivery_status"), ga("status"))

              delta = _safe_int(ga("Delta"), target - count_dl)
              upstream_type = ga("Type") or ""

              self._groups.append({
                  "group_scope": group_scope,
                  "group_id": group_id,
                  "target": target,
                  "count_dl": count_dl,
                  "delta": delta,
                  "n_lu": n_lu,
                  "jvids": jvids,
                  "bus_numbers": bns,
                  "statuses": sts,
                  "delivery_statuses": ds,
                  "upstream_type": upstream_type,
                  "ctx": {
                      "Delta": ga("Delta"),
                      "BG_ID": bg_id,
                      "MDU_ID": md_id,
                      "Type": upstream_type,
                  },
              })

          def close(self):
              for group in self._groups:
                  lu_rows = reconcile_group(group)

                  _enrich_feedback_ollama(
                      lu_rows,
                      group_id=group["group_id"],
                      target=group["target"],
                      count_dl=group["count_dl"],
                      ctx_attrs={k: v for k, v in group["ctx"].items() if v},
                  )

                  for lu in lu_rows:
                      out = fmeobjects.FMEFeature()

                      # ── LU-level attributes ──
                      out.setAttribute("jvid", lu.get("jvid") or "")
                      out.setAttribute("bus_number", lu.get("bus_number") or "")
                      out.setAttribute("status", lu.get("status") or "")
                      out.setAttribute("delivery_status",
                                       "" if lu.get("delivery_status") is None
                                       else str(lu["delivery_status"]))

                      act = str(lu.get("action") or "KEEP").strip().upper()
                      if act not in ("KEEP", "REMOVE", "ADD"):
                          act = "KEEP"
                      out.setAttribute("action", act)
                      out.setAttribute("LU_ACTION", act)
                      out.setAttribute("feedback", lu.get("feedback") or "")

                      # ── Address-level attributes (SSV review) ──
                      fa = str(lu.get("final_action") or "Keep")
                      if fa not in ("Keep", "Add", "Remove", "Modify", "Review"):
                          fa = "Keep"
                      out.setAttribute("final_action", fa)
                      out.setAttribute("action_reason", lu.get("action_reason") or "")
                      out.setAttribute("type", lu.get("type") or "")
                      out.setAttribute("lu_count_bl", int(lu.get("lu_count_bl", 0)))
                      out.setAttribute("lu_count_ssv", int(lu.get("lu_count_ssv", 0)))

                      # ── Group identifiers ──
                      out.setAttribute("group_scope", lu.get("group_scope") or "")
                      out.setAttribute("group_id", lu.get("group_id") or "")
                      out.setAttribute("upstream_type", lu.get("upstream_type") or "")
                      out.setAttribute("Delta", str(lu.get("delta", "")))

                      ctx = group["ctx"]
                      if ctx.get("BG_ID"):
                          out.setAttribute("BG_ID", ctx["BG_ID"])
                      if ctx.get("MDU_ID"):
                          out.setAttribute("MDU_ID", ctx["MDU_ID"])

                      self.pyoutput(out)


      # ───────────────────────────────────────────────────────────────────────────
      # FME PythonCaller — output attributes to expose:
      #
      #   action           varchar(20)     KEEP / REMOVE / ADD  (per LU)
      #   LU_ACTION        varchar(20)     mirror of action
      #   final_action     varchar(20)     Keep / Add / Remove / Modify / Review  (per address)
      #   action_reason    varchar(500)    why final_action was assigned
      #   type             varchar(10)     MDU / SDU  (current or updated)
      #   lu_count_bl      int32           LU count from Build List
      #   lu_count_ssv     int32           LU count from SSV
      #   feedback         varchar(2000)   per-LU explanation
      #   jvid             varchar(200)    LU address key
      #   bus_number       varchar(200)    unit identifier
      #   status           varchar(255)    LU status
      #   delivery_status  varchar(200)    LU delivery status
      #   group_scope      varchar(20)     BG / MDU
      #   group_id         varchar(200)    BG_ID or MDU_ID value
      #   upstream_type    varchar(200)    Type from AttributeCreator_3
      #   BG_ID            varchar(200)    Building Group ID (if BG path)
      #   MDU_ID           varchar(200)    MDU ID (if MDU path)
      #   Delta            varchar(200)    SSV total - BL total
      # ───────────────────────────────────────────────────────────────────────────
    PYTHONSYMBOL = FeatureProcessor

Bookmark: LU Reconcilitation
In_scope: AttributeCreator
    ATTR_TABLE = SET_TO in_scope (logical) = true
    INPUT_PORT_CONNECTED = CONNECTED
    -> PythonCaller_2
In_scope_2: AttributeCreator
    ATTR_TABLE = SET_TO in_scope (logical) = false
    INPUT_PORT_CONNECTED = CONNECTED
    -> PythonCaller_2
PythonCaller_2
    HIDE_ATTRIBUTES = address_source "APP SSV QUADRANT" appartment_number area_id area_pop_id belmap_address_id belmap_building_id building_group building_type central_pop_id city delivery_status Delta Depl_type fme_rejection_code fme_rejection_message home_released home_released_date in_scope jvid_use lot municipality postal_code scopelist_v2 scopelist_v15 sdu_exceptional street_name twin_jvid x y
    INPUT_PORT_CONNECTED = CONNECTED
    NEW_ATTRIBUTES = MDU_ID int16 BG_ID int16 house_number int16 house_number_extension int16 jvid int16 bus_number buffer status buffer delivery_status buffer action buffer feedback buffer
    PYTHONSOURCE:
      # -*- coding: utf-8 -*-
      """
      LU Reconciliation PythonCaller — v2 (LU-Level Input Edition).

      Spec: lu_reconciliation_requirements_v2.md

      Two named input ports:
        INPUT     — in-scope LU rows (primary reconciliation dataset)
        OOS_INPUT — out-of-scope LU rows (pool for reuse before synthetic ADD)

      Self-groups features by BG_ID (priority) or MDU_ID.
      Target LU count = BG_Total (when BG_ID present) or MDU_Total.
      Current LU count = number of in-scope features in the group.

      Actions: KEEP, REMOVE, REUSE, ADD.
      ADD slots filled in priority order:
        1. OOS LUs with scopelist_v15 populated
        2. OOS LUs without scopelist_v15
        3. Synthetic ADD rows (bus_number suggested algorithmically)

      Ollama integration (optional, env OLLAMA_ENABLED):
        After deterministic logic, Ollama reviews edge cases:
        - REMOVE: validates which LUs to remove when candidates are ambiguous
        - ADD: validates/improves suggested bus_numbers for irregular patterns

      FME: Class FeatureProcessor, Symbol FeatureProcessor.
           FME 2024.2, Python 3.12.
      """

      from __future__ import annotations

      import json
      import os
      import re
      import ssl
      import urllib.error
      import urllib.request
      from collections import Counter, defaultdict

      import fmeobjects


      # ───────────────────────────────────────────────────────────────────────────
      # Attribute helpers
      # ───────────────────────────────────────────────────────────────────────────

      def _get_attr(feature, name):
          try:
              v = feature.getAttribute(name)
          except Exception:
              v = None
          if v is None:
              return None
          s = str(v).strip()
          return s if s not in ("", "None") else None

      def _safe_int(val, default=0):
          try:
              return int(float(str(val)))
          except (ValueError, TypeError):
              return default

      def _group_key(lu):
          """Resolve grouping key: BG_ID (priority) or MDU_ID. None if ungroupable."""
          bg = lu.get("BG_ID")
          if bg:
              return ("BG", bg)
          md = lu.get("MDU_ID")
          if md:
              return ("MDU", md)
          return None


      # ───────────────────────────────────────────────────────────────────────────
      # Ollama helpers (optional — edge-case advisor for REMOVE / ADD decisions)
      #
      # Env vars: OLLAMA_ENABLED (default "1"), OLLAMA_HOST, OLLAMA_MODEL,
      #           OLLAMA_TIMEOUT.
      # Fails silently — deterministic logic always runs first.
      # ───────────────────────────────────────────────────────────────────────────

      def _ollama_enabled():
          return os.environ.get(
              "OLLAMA_ENABLED", "1").strip() not in ("0", "false", "no", "")

      def _ollama_chat(messages, *, model=None):
          host = os.environ.get(
              "OLLAMA_HOST", "http://127.0.0.1:11434").rstrip("/")
          m = model or os.environ.get("OLLAMA_MODEL", "llama3.2").strip()
          try:
              timeout = int(os.environ.get("OLLAMA_TIMEOUT", "120"))
          except ValueError:
              timeout = 120
          data = json.dumps({
              "model": m, "messages": messages,
              "stream": False, "options": {"temperature": 0.1},
          }).encode()
          req = urllib.request.Request(
              f"{host}/api/chat", data=data,
              headers={"Content-Type": "application/json"}, method="POST",
          )
          ctx = ssl.create_default_context()
          with urllib.request.urlopen(req, timeout=timeout, context=ctx) as resp:
              body = json.loads(resp.read().decode())
          return str(body.get("message", {}).get("content", "")).strip()

      def _ollama_json(raw):
          """Extract first JSON object from LLM response."""
          m = re.search(r"\{[\s\S]*\}", (raw or "").strip())
          if not m:
              return None
          try:
              return json.loads(m.group(0))
          except json.JSONDecodeError:
              return None


      def ollama_review_removals(in_lus, to_remove_indices, group_id):
          """
          Ask Ollama to review REMOVE decisions for edge cases.

          Sends the full LU list with current action assignments.
          Returns a dict {index: note} to append to feedback, or empty.
          """
          if not _ollama_enabled() or not to_remove_indices:
              return {}
          rows = []
          for i, lu in enumerate(in_lus):
              rows.append(
                  f"{i}<pipe>bus={lu.get('bus_number','')!r}"
                  f"<pipe>delivery_status={lu.get('delivery_status','')!r}"
                  f"<pipe>status={lu.get('status','')!r}"
                  f"<pipe>action={lu.get('action','')}")
          system = (
              "You are a Belgian fiber deployment assistant reviewing LU "
              "removal decisions for an MDU/BG group. "
              "Output ONLY valid JSON, no markdown. "
              'Schema: {"notes": {"<index>": "<note>", ...}} '
              "Only include entries where you see a concern or useful context. "
              "Each note max 30 words. Do not contradict locked/HOMES_CONNECT "
              "decisions."
          )
          user = (
              f"Group={group_id!r}. "
              f"Indices marked REMOVE: {sorted(to_remove_indices)}.\n"
              f"LU rows:\n" + "\n".join(rows)
          )
          try:
              raw = _ollama_chat([
                  {"role": "system", "content": system},
                  {"role": "user", "content": user}])
              parsed = _ollama_json(raw)
              if not parsed or "notes" not in parsed:
                  return {}
              notes = parsed["notes"]
              if not isinstance(notes, dict):
                  return {}
              return {int(k): str(v).strip()
                      for k, v in notes.items()
                      if str(v).strip()}
          except (urllib.error.URLError, urllib.error.HTTPError,
                  TimeoutError, OSError, json.JSONDecodeError,
                  ValueError, KeyError):
              return {}


      def ollama_review_additions(existing_bns, suggestions, group_id):
          """
          Ask Ollama to validate/improve bus_number suggestions for ADD rows.

          Returns a list of replacement suggestions (same length), or None
          if Ollama can't improve.
          """
          if not _ollama_enabled() or not suggestions:
              return None
          system = (
              "You are a Belgian fiber deployment assistant. "
              "Review bus_number suggestions for new LUs being added to an MDU/BG. "
              "Output ONLY valid JSON, no markdown. "
              'Schema: {"suggestions": ["val1", ...], "changed": true/false} '
              "Return changed=false if the original suggestions are fine. "
              "If you improve them, return the full list with changed=true. "
              "New values must NOT duplicate any existing bus_number. "
              "Follow the dominant prefix+digit pattern of existing values."
          )
          user = (
              f"Group={group_id!r}.\n"
              f"Existing bus_numbers: {existing_bns!r}\n"
              f"Algorithm suggestions: {suggestions!r}\n"
              "Are these suggestions correct for this building's pattern?"
          )
          try:
              raw = _ollama_chat([
                  {"role": "system", "content": system},
                  {"role": "user", "content": user}])
              parsed = _ollama_json(raw)
              if not parsed:
                  return None
              if not parsed.get("changed", False):
                  return None
              new_sugg = parsed.get("suggestions")
              if (not isinstance(new_sugg, list)
                      or len(new_sugg) != len(suggestions)):
                  return None
              # Validate: no duplicates with existing
              used = set(b.strip() for b in existing_bns if b and b.strip())
              for s in new_sugg:
                  if not isinstance(s, str) or not s.strip():
                      return None
                  if s.strip() in used:
                      return None
              return [s.strip() for s in new_sugg]
          except (urllib.error.URLError, urllib.error.HTTPError,
                  TimeoutError, OSError, json.JSONDecodeError,
                  ValueError, KeyError):
              return None


      # ───────────────────────────────────────────────────────────────────────────
      # Bus-number logic (§7, §8, §9)
      # ───────────────────────────────────────────────────────────────────────────

      def _parse_busnum(bn):
          if not bn:
              return None
          m = re.fullmatch(r"([A-Za-z]*)(\d+)", bn.strip())
          if m:
              return m.group(1).upper(), m.group(2), int(m.group(2))
          return None

      def _sort_key(bn):
          """§9 — logical sort order for bus_numbers."""
          if not bn or not bn.strip():
              return (2, "", 0, "")
          p = _parse_busnum(bn.strip())
          if p:
              return (0, p[0], p[2], "")
          return (1, "", 0, bn.strip().lower())

      def _normalize_busnum(bn):
          """§7.3 — normalize for duplicate detection."""
          if not bn:
              return ""
          s = bn.strip().lower()
          for pfx in ("bte", "box", "apt", "app", "flat", "unit"):
              if s.startswith(pfx):
                  s = s[len(pfx):]
                  break
          return s.lstrip("0") or "0"

      def detect_outliers(bus_numbers):
          """§7 — return set of outlier indices."""
          outlier_idx = set()
          parsed = [_parse_busnum(bn) if bn and bn.strip() else None
                    for bn in bus_numbers]
          prefixes = [p[0] for p in parsed if p is not None]
          if not prefixes:
              return outlier_idx

          prefix_counts = Counter(prefixes)
          dominant_prefix, dom_count = prefix_counts.most_common(1)[0]

          # §7.1 Non-dominant prefix
          if dom_count > 1:
              for i, p in enumerate(parsed):
                  if p is not None and p[0] != dominant_prefix:
                      outlier_idx.add(i)

          # §7.2 Wrong digit length (skip if range spans power-of-10 boundary)
          dom_group = [i for i, p in enumerate(parsed)
                       if p is not None and p[0] == dominant_prefix
                       and i not in outlier_idx]
          dominant_dl = None
          if dom_group:
              nums = [parsed[i][2] for i in dom_group]
              range_spans = len(str(min(nums))) != len(str(max(nums)))
              dl_counts = Counter(len(parsed[i][1]) for i in dom_group)
              dominant_dl = dl_counts.most_common(1)[0][0]
              if not range_spans and dl_counts.most_common(1)[0][1] > 1:
                  for i in dom_group:
                      if len(parsed[i][1]) != dominant_dl:
                          outlier_idx.add(i)

          # §7.3 Duplicate normalisation
          norm_map = {}
          for i, bn in enumerate(bus_numbers):
              if i in outlier_idx or not bn or not bn.strip():
                  continue
              norm = _normalize_busnum(bn)
              if norm in norm_map:
                  other = norm_map[norm]
                  def _is_dom(p):
                      if p is None:
                          return False
                      ok = p[0] == dominant_prefix
                      if dominant_dl is not None:
                          ok = ok and len(p[1]) == dominant_dl
                      return ok
                  if _is_dom(parsed[i]) and not _is_dom(parsed[other]):
                      outlier_idx.add(other)
                      norm_map[norm] = i
                  else:
                      outlier_idx.add(i)
              else:
                  norm_map[norm] = i
          return outlier_idx

      def suggest_bus_numbers(existing, n_add):
          """§8 — suggest n_add new bus_numbers following the dominant pattern."""
          if n_add <= 0:
              return []
          clean = [b for b in existing if b and b.strip()]
          outliers = detect_outliers(clean)
          pool = [b for i, b in enumerate(clean) if i not in outliers]
          parsed_pool = [p for p in (_parse_busnum(b) for b in pool)
                         if p is not None]
          used = set(b.strip() for b in clean)

          if not parsed_pool:
              sugg, c = [], 1
              while len(sugg) < n_add:
                  if str(c) not in used:
                      sugg.append(str(c))
                  c += 1
              return sugg

          prefix_counts = Counter(p[0] for p in parsed_pool)
          dom_prefix = prefix_counts.most_common(1)[0][0]
          dom_parsed = [p for p in parsed_pool if p[0] == dom_prefix]
          dl_counts = Counter(len(p[1]) for p in dom_parsed)
          pad_len = dl_counts.most_common(1)[0][0]
          nums = [p[2] for p in dom_parsed]

          if len(nums) == 1:
              sugg, nv = [], nums[0] + 1
              while len(sugg) < n_add:
                  c = dom_prefix + str(nv).zfill(pad_len)
                  if c not in used:
                      sugg.append(c)
                  nv += 1
              return sugg

          padded = [str(v).zfill(pad_len) for v in nums]
          pos_vals = [set(s[pos] for s in padded) for pos in range(pad_len)]
          varying = [i for i, vs in enumerate(pos_vals) if len(vs) > 1]
          fixed = {i: list(vs)[0] for i, vs in enumerate(pos_vals)
                   if len(vs) == 1}

          if not varying:
              sugg, nv = [], max(nums) + 1
              while len(sugg) < n_add:
                  c = dom_prefix + str(nv).zfill(pad_len)
                  if c not in used:
                      sugg.append(c)
                  nv += 1
              return sugg

          floor_pos = varying[0]
          inner = varying[1:]
          max_floor = max(int(s[floor_pos]) for s in padded)
          inner_combos = sorted(set(
              tuple(s[p] for p in inner) for s in padded
          )) if inner else [()]

          sugg = []
          nf = max_floor + 1
          while len(sugg) < n_add and nf <= 99:
              for combo in inner_combos:
                  if len(sugg) >= n_add:
                      break
                  chars = ["0"] * pad_len
                  for p, d in fixed.items():
                      chars[p] = d
                  chars[floor_pos] = str(nf)
                  for p, d in zip(inner, combo):
                      chars[p] = d
                  c = dom_prefix + "".join(chars)
                  if c not in used:
                      sugg.append(c)
                      used.add(c)
              nf += 1

          if len(sugg) < n_add:
              nv = max(nums) + 1
              while len(sugg) < n_add:
                  c = dom_prefix + str(nv).zfill(pad_len)
                  if c not in used:
                      sugg.append(c)
                      used.add(c)
                  nv += 1
          return sugg


      # ───────────────────────────────────────────────────────────────────────────
      # Core reconciliation (§4, §5, §6)
      # ───────────────────────────────────────────────────────────────────────────

      def process_group(in_lus, oos_lus, group_key):
          """
          §4–§6. Reconcile one group.

          in_lus:   list of dicts — in-scope LUs (from INPUT port).
          oos_lus:  list of dicts — out-of-scope LUs (from OOS_INPUT port).
          Returns:  list of dicts — all output LUs (KEEP/REMOVE/REUSE/ADD).
          """
          scope, gid = group_key
          first = in_lus[0]
          if scope == "BG":
              target = _safe_int(first.get("BG_Total"), 0)
          else:
              target = _safe_int(first.get("MDU_Total"), 0)

          # §4.2 current count = in-scope LUs only
          n_lu = len(in_lus)

          # Initialise action/feedback on every in-scope LU
          for lu in in_lus:
              lu["action"] = "KEEP"
              lu["feedback"] = ""

          # §4.3 Pre-existing duplicate bus_number warning (scoped per address)
          addr_bn_count = Counter(
              (lu.get("house_number") or "", lu.get("house_number_extension") or "",
               lu.get("bus_number") or "")
              for lu in in_lus if lu.get("bus_number"))
          for lu in in_lus:
              bn = lu.get("bus_number") or ""
              addr_key = (lu.get("house_number") or "",
                          lu.get("house_number_extension") or "", bn)
              if bn and addr_bn_count[addr_key] > 1:
                  lu["feedback"] = (
                      f"Warning: duplicate bus_number ({bn}) in source data")

          n_remove = max(n_lu - target, 0)
          n_add = max(target - n_lu, 0)

          if n_remove == 0 and n_add == 0:
              return list(in_lus)

          # ── §5 REMOVE logic ──
          if n_remove > 0:
              locked = [False] * n_lu

              # §5.1 Lock HOMES_CONNECT
              for i, lu in enumerate(in_lus):
                  if (lu.get("status") or "").strip().upper() == "HOMES_CONNECT":
                      locked[i] = True

              # §5.1 Lock NULL bus_number when MDU becoming SDU (target=1)
              if target == 1:
                  for i, lu in enumerate(in_lus):
                      if not lu.get("bus_number"):
                          locked[i] = True
                          lu["feedback"] = (
                              "Kept: NULL bus_number retained (MDU becoming SDU)")
                          break

              unlocked = [i for i in range(n_lu) if not locked[i]]

              # §5.2 Uniform delivery_status check
              unlocked_ds = set(
                  str(in_lus[i].get("delivery_status") or "")
                  for i in unlocked)
              ds_uniform = len(unlocked_ds) <= 1

              # §5.2 Candidate flagging (scoped per address for outliers & duplicates)
              def _addr_key(lu):
                  return (lu.get("house_number") or "",
                          lu.get("house_number_extension") or "")

              # Group unlocked indices by address for per-address outlier detection
              addr_groups = defaultdict(list)
              for i in unlocked:
                  addr_groups[_addr_key(in_lus[i])].append(i)

              outlier_set = set()
              for addr, indices in addr_groups.items():
                  addr_bns = [in_lus[i].get("bus_number") or "" for i in indices]
                  for j in detect_outliers(addr_bns):
                      outlier_set.add(indices[j])

              # Track seen bus_numbers per address
              seen_bn = {}  # (addr_key, bn) -> index
              cand_flags = {i: [] for i in unlocked}

              for i in unlocked:
                  ds = str(in_lus[i].get("delivery_status") or "")
                  bn = in_lus[i].get("bus_number") or ""
                  addr = _addr_key(in_lus[i])

                  if not ds_uniform:
                      if ds and ds.startswith("2"):
                          cand_flags[i].append(
                              "delivery_status starts with 2")
                      if ds and not ds.endswith("5"):
                          cand_flags[i].append(
                              "delivery_status not ending with 5")

                  if not bn and len(unlocked) > 1:
                      cand_flags[i].append("bus_number is empty/null")
                  if i in outlier_set:
                      cand_flags[i].append(f"bus_number outlier ({bn})")
                  if bn:
                      dup_key = (addr, bn)
                      if dup_key in seen_bn:
                          cand_flags[i].append(
                              f"duplicate bus_number ({bn})")
                      else:
                          seen_bn[dup_key] = i

              # §5.3 Remove candidates first, then rest (from end)
              candidates = sorted(
                  [i for i in unlocked if cand_flags[i]],
                  key=lambda i: _sort_key(
                      in_lus[i].get("bus_number") or ""))
              non_candidates = sorted(
                  [i for i in unlocked if not cand_flags[i]],
                  key=lambda i: _sort_key(
                      in_lus[i].get("bus_number") or ""))

              to_remove = set()
              remaining = n_remove
              while remaining > 0 and candidates:
                  to_remove.add(candidates.pop())
                  remaining -= 1
              while remaining > 0 and non_candidates:
                  to_remove.add(non_candidates.pop())
                  remaining -= 1

              for i in unlocked:
                  if i in to_remove:
                      flags = cand_flags[i]
                      in_lus[i]["action"] = "REMOVE"
                      in_lus[i]["feedback"] = (
                          ("Remove: " + ", ".join(flags)) if flags
                          else "Remove: removed from end (no candidate flags)")
                  elif cand_flags[i]:
                      in_lus[i]["feedback"] = (
                          "Kept (candidate but not needed): "
                          + ", ".join(cand_flags[i]))

              # Ollama: review removal edge cases
              notes = ollama_review_removals(in_lus, to_remove, gid)
              for idx, note in notes.items():
                  if 0 <= idx < n_lu:
                      base = (in_lus[idx].get("feedback") or "").strip()
                      in_lus[idx]["feedback"] = (
                          f"{base} [LLM: {note}]" if base else f"[LLM: {note}]")

              return list(in_lus)

          # ── §6 ADD logic ──
          results = list(in_lus)

          if n_add > 0:
              # Collect in-scope bus_numbers for duplicate checking
              in_scope_norms = {}
              for lu in in_lus:
                  bn = lu.get("bus_number") or ""
                  if bn:
                      in_scope_norms[_normalize_busnum(bn)] = bn

              # Group-level fields for REUSE/ADD inheritance (§6.3, §6.4)
              group_fields = {
                  "MDU_ID": first.get("MDU_ID") or "",
                  "BG_ID": first.get("BG_ID") or "",
                  "house_number": first.get("house_number") or "",
                  "house_number_extension": (
                      first.get("house_number_extension") or ""),
              }

              filled = 0

              # §6.1 Priority 1: OOS with scopelist_v15 populated
              oos_priority = [lu for lu in oos_lus
                              if lu.get("scopelist_v15")]
              # §6.1 Priority 2: OOS without scopelist_v15
              oos_normal = [lu for lu in oos_lus
                            if not lu.get("scopelist_v15")]

              for oos_pool in [oos_priority, oos_normal]:
                  for oos_lu in oos_pool:
                      if filled >= n_add:
                          break

                      # §6.2 Bus number duplicate check
                      oos_bn = oos_lu.get("bus_number") or ""
                      is_dup = False
                      if oos_bn:
                          norm = _normalize_busnum(oos_bn)
                          if norm in in_scope_norms:
                              is_dup = True

                      # §6.3 Build REUSE row — carry all original fields
                      reuse_lu = dict(oos_lu)
                      reuse_lu["action"] = "REUSE"

                      sv15 = oos_lu.get("scopelist_v15")
                      if sv15:
                          reuse_lu["feedback"] = (
                              f"Reused OOS LU \u2014 scopelist_v15: {sv15}")
                      else:
                          reuse_lu["feedback"] = (
                              "Reused OOS LU \u2014 no scopelist_v15")

                      if is_dup:
                          reuse_lu["feedback"] += (
                              f"; Warning: duplicate bus_number ({oos_bn})"
                              " with in-scope LU")

                      # Override group identifiers from in-scope
                      for k, v in group_fields.items():
                          reuse_lu[k] = v

                      results.append(reuse_lu)

                      # Track this bus_number as used
                      if oos_bn:
                          in_scope_norms[_normalize_busnum(oos_bn)] = oos_bn

                      filled += 1

              # §6.4 Synthetic ADD rows for remaining unfilled slots
              remaining_add = n_add - filled
              if remaining_add > 0:
                  # Include all bus_numbers so far (in-scope + REUSE)
                  all_bns = [lu.get("bus_number") or "" for lu in results
                             if lu.get("bus_number")]
                  suggestions = suggest_bus_numbers(all_bns, remaining_add)

                  # Ollama: review/improve suggestions for irregular patterns
                  improved = ollama_review_additions(all_bns, suggestions, gid)
                  if improved:
                      suggestions = improved

                  for k in range(remaining_add):
                      suggested = (suggestions[k]
                                   if k < len(suggestions) else "")
                      fb = f"New LU \u2014 suggested bus_number: {suggested}"
                      if improved:
                          fb += " [LLM-reviewed]"
                      add_lu = {
                          "jvid": "",
                          "bus_number": suggested,
                          "status": "",
                          "delivery_status": "",
                          "action": "ADD",
                          "feedback": fb,
                      }
                      # §6.4 Inherit group fields
                      for gk, gv in group_fields.items():
                          add_lu[gk] = gv

                      results.append(add_lu)

          return results


      # ───────────────────────────────────────────────────────────────────────────
      # FME FeatureProcessor (§10)
      # ───────────────────────────────────────────────────────────────────────────

      # §10.3 Output attributes
      _OUTPUT_ATTRS = [
          "MDU_ID", "BG_ID", "house_number", "house_number_extension",
          "jvid", "bus_number", "status", "delivery_status",
          "action", "feedback",
      ]


      class FeatureProcessor(object):
          """§10.1 — batch mode with two input ports."""

          def __init__(self):
              self._in_scope = []
              self._oos = []

          def input(self, feature):
              """§10.2 — route by input port name."""
              # FME sets feature type to the input port name
              port = (feature.getFeatureType() or "").strip()

              lu = {}
              for attr in _OUTPUT_ATTRS:
                  lu[attr] = _get_attr(feature, attr)
              # Additional attrs needed for logic but not in output list
              lu["scopelist_v15"] = _get_attr(feature, "scopelist_v15")
              lu["MDU_Total"] = _get_attr(feature, "MDU_Total")
              lu["BG_Total"] = _get_attr(feature, "BG_Total")
              lu["Delta"] = _get_attr(feature, "Delta")

              if port == "OOS_INPUT":
                  self._oos.append(lu)
              else:
                  self._in_scope.append(lu)

          def close(self):
              """§10.2 — self-group and process."""
              in_scope_by_group = defaultdict(list)
              oos_by_group = defaultdict(list)
              ungroupable = []

              for lu in self._in_scope:
                  key = _group_key(lu)
                  if key is None:
                      ungroupable.append(lu)
                  else:
                      in_scope_by_group[key].append(lu)

              for lu in self._oos:
                  key = _group_key(lu)
                  if key is not None:
                      oos_by_group[key].append(lu)

              # §2.3 Ungroupable LUs — pass through as KEEP
              for lu in ungroupable:
                  lu["action"] = "KEEP"
                  lu["feedback"] = (
                      "Kept: no grouping key "
                      "(BG_ID and MDU_ID both absent)")
                  self._emit(lu)

              # Process each group
              for gkey in in_scope_by_group:
                  in_lus = in_scope_by_group[gkey]
                  oos_lus = oos_by_group.get(gkey, [])
                  results = process_group(in_lus, oos_lus, gkey)
                  for lu in results:
                      self._emit(lu)

          def _emit(self, lu):
              out = fmeobjects.FMEFeature()
              for attr in _OUTPUT_ATTRS:
                  val = lu.get(attr)
                  out.setAttribute(
                      attr, str(val) if val is not None else "")
              self.pyoutput(out)
    PYTHONSYMBOL = FeatureProcessor
    -> AttributeFilter

Bookmark: Stats
TestFilter_4
    DEFAULT_VALUE = <UNFILTERED>
    PASSED_TEST_GROUP_OUTPUT = FIRST
    TEST_LIST = "BOOL_OP,OR,COMPOSITE_TEST,""""""1"""""",TEST_CLAUSE,TEST BG_ID ATTRIBUTE_HAS_A_VALUE """,BG ID
    BG ID -> DuplicateFilter_4
    <UNFILTERED> -> TestFilter_5
DuplicateFilter_4
    INPUT_ORDERED_CHOICE_LOOKUP = NO
    KEYATTR = BG_ID
    INPUT_ORDERED_CHOICE = No
    UNIQUE -> TestFilter_5
TestFilter_5
    DEFAULT_VALUE = <UNFILTERED>
    PASSED_TEST_GROUP_OUTPUT = FIRST
    TEST_LIST = "BOOL_OP,OR,COMPOSITE_TEST,""""""1"""""",TEST_CLAUSE,TEST MDU_ID ATTRIBUTE_HAS_A_VALUE """,MDU ID
    MDU ID -> DuplicateFilter_5
    <UNFILTERED> -> StatisticsCalculator_3
DuplicateFilter_5
    INPUT_ORDERED_CHOICE_LOOKUP = NO
    KEYATTR = MDU_ID
    INPUT_ORDERED_CHOICE = No
    UNIQUE -> StatisticsCalculator_3
StatisticsCalculator_3
    ATTR_ACCUM_MODE = None
    CALCULATION_MODE = NUMERIC
    FEAT_STATS = Delta,NUMERIC_MODE,,,,SUM,,,,,,,,,
    SUMMARY -> AttributeManager_4
