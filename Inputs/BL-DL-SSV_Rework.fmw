FME workspace BL-DL-SSV_Rework.fmw

Parameters:
- SourceDataset_POSTGIS = Unifiber - AH   # Connection
- DMP_Area_Area_ID = UF026-01   # DMP AREA AREA ID
- Area_ID = 32

Readers:
- POSTGIS_1: POSTGIS from $(SourceDataset_POSTGIS)

AttributeCreator_3
    ATTR_TABLE = SET_TO Type (varchar(200)) = FME_CONDITIONAL:DEFAULT_VALUE'_FME_NO_OP_'BOOL_OP;OR;COMPOSITE_TEST;1;TEST DMP_delivery_status ATTRIBUTE_IS_MISSING _FME_BLANK_STRING_'New MDU'BOOL_OP;COMPOSITE;COMPOSITE_TEST;( 1 OR 2 OR 3 OR 4 OR 5 ) AND ( 6 );TEST @Value(APP SSV QUADRANT) = A;TEST @Value(APP SSV QUADRANT) = Ax;TEST @Value(APP SSV QUADRANT) = C;TEST @Value(APP SSV QUADRANT) = Cx;TEST @Value(APP SSV QUADRANT) = Dx;TEST @Value(Count_BL) = 1'SDU to MDU in Q Dx,C,Cx,A,Ax'BOOL_OP;COMPOSITE;COMPOSITE_TEST;1 AND 2 AND 3;TEST @Value(APP SSV QUADRANT) = D;TEST @Value(Count_BL) = 1;TEST @Value(APP SSV TOTAL UNITS) <= 4'SDU to MDU in QD - Spare'BOOL_OP;COMPOSITE;COMPOSITE_TEST;1 AND 2 AND 3;TEST @Value(APP SSV QUADRANT) = D;TEST @Value(Count_BL) = 1;TEST @Value(APP SSV TOTAL UNITS) > 4'SDU to MDU in QD - no Spare'BOOL_OP;COMPOSITE;COMPOSITE_TEST;1 OR 2 AND ( 3 );TEST @Value(APP SSV QUADRANT) = M;TEST @Value(APP SSV QUADRANT) = P;TEST @Value(Count_BL) = 1'QM and QP'BOOL_OP;COMPOSITE;COMPOSITE_TEST;( 1 OR 2 OR 3 OR 4 ) AND 5 AND 6 AND 7;TEST @Value(APP SSV QUADRANT) = A;TEST @Value(APP SSV QUADRANT) = Ax;TEST @Value(APP SSV QUADRANT) = C;TEST @Value(APP SSV QUADRANT) = Cx;TEST @Value(Count_BL) > 1;TEST @Left(@Value(DMP_delivery_status),1) = 7;TEST @Evaluate(@sub(@Value(APP SSV TOTAL UNITS),@Value(Count_BL))) <= @max(1,@mult(0.2,@Value(Count_BL)))'Q C,Cx,A,Ax - UG Distribution -  spare'BOOL_OP;COMPOSITE;COMPOSITE_TEST;( 1 OR 2 OR 3 OR 4 ) AND 5 AND 6 AND 7;TEST @Value(APP SSV QUADRANT) = A;TEST @Value(APP SSV QUADRANT) = Ax;TEST @Value(APP SSV QUADRANT) = C;TEST @Value(APP SSV QUADRANT) = Cx;TEST @Value(Count_BL) > 1;TEST @Left(@Value(DMP_delivery_status),1) = 7;TEST @Evaluate(@sub(@Value(APP SSV TOTAL UNITS),@Value(Count_BL))) > @max(1,@mult(0.2,@Value(Count_BL)))'Q C,Cx,A,Ax - UG Distribution - no spare'BOOL_OP;COMPOSITE;COMPOSITE_TEST;( 1 OR 2 OR 3 OR 4 ) AND 5 AND 6;TEST @Value(APP SSV QUADRANT) = A;TEST @Value(APP SSV QUADRANT) = Ax;TEST @Value(APP SSV QUADRANT) = C;TEST @Value(APP SSV QUADRANT) = Cx;TEST @Value(Count_BL) > 1;TEST @Left(@Value(DMP_delivery_status),1) = 8'Q C,Cx,A,Ax - Facade Distribution 'BOOL_OP;COMPOSITE;COMPOSITE_TEST;( 1 OR 2 OR 3 OR 4 ) AND 5 AND 6 AND 7;TEST @Value(APP SSV QUADRANT) = A;TEST @Value(APP SSV QUADRANT) = Ax;TEST @Value(APP SSV QUADRANT) = C;TEST @Value(APP SSV QUADRANT) = Cx;TEST @Value(Count_BL) > 1;TEST @Left(@Value(DMP_delivery_status),1) = 9;TEST @Evaluate(@sub(@Value(APP SSV TOTAL UNITS),@Value(Count_BL))) <= @max(1,@mult(0.2,@Value(Count_BL)))'Q C,Cx,A,Ax - Aerial Distribution - Spare'BOOL_OP;COMPOSITE;COMPOSITE_TEST;( 1 OR 2 OR 3 OR 4 ) AND 5 AND 6 AND 7;TEST @Value(APP SSV QUADRANT) = A;TEST @Value(APP SSV QUADRANT) = Ax;TEST @Value(APP SSV QUADRANT) = C;TEST @Value(APP SSV QUADRANT) = Cx;TEST @Value(Count_BL) > 1;TEST @Left(@Value(DMP_delivery_status),1) = 9;TEST @Evaluate(@sub(@Value(APP SSV TOTAL UNITS),@Value(Count_BL))) > @max(1,@mult(0.2,@Value(Count_BL)))'Q C,Cx,A,Ax - Aerial Distribution - no Spare'BOOL_OP;COMPOSITE;COMPOSITE_TEST;( 1 OR 2 ) AND 3 AND 4;TEST @Value(APP SSV QUADRANT) = D;TEST @Value(APP SSV QUADRANT) = Dx;TEST @Value(Count_BL) > 1;TEST @Value(APP SSV TOTAL UNITS) <= @mult(@add(@round(@div(@Value(Count_BL),4),0),1),4)'Q D,Dx - Spare'BOOL_OP;COMPOSITE;COMPOSITE_TEST;( 1 OR 2 ) AND 3 AND 4;TEST @Value(APP SSV QUADRANT) = D;TEST @Value(APP SSV QUADRANT) = Dx;TEST @Value(Count_BL) > 1;TEST @Value(APP SSV TOTAL UNITS) > @mult(@add(@round(@div(@Value(Count_BL),4),0),1),4)'Q D,Dx - no Spare'BOOL_OP;OR;COMPOSITE_TEST;1;TEST APP SSV QUADRANT NOT_ATTRIBUTE_HAS_A_VALUE _FME_BLANK_STRING_'No SSV'FME_NUM_CONDITIONS14___

Bookmark: Inputs
MONDAY_ITEM_VIEW_GEOM (reader POSTGIS_1)
    attributes: item_id int8, task text, Doubles text, DMP AREA AREA ID text, DMP AREA NAME text, DMP POSTAL CODE text, DMP MUNICIPALITY text, DMP CITY text, DMP STREET text, DMP HOUSENUMBER text, DMP BUILDING KEY text, DMP BELMAP LU COUNT text, DMP POP AREA NAME text, DMP IN SCOPE text, APP SSV BLDG GRP INDIV TREATMENT text, APP SSV BLDG GRP MAIN ADDRESS text, APP SSV BU COUNT text, APP SSV BUILDING GROUP text, APP SSV BUILDING TYPE text, APP SSV DEPLOYMENT TYPE text, APP SSV LOW FLOOR text, APP SSV LU COUNT text, APP SSV QUADRANT text, APP SSV SU COUNT text, APP SSV TOTAL UNITS text, APP SSV UPPER FLOOR text, SSV ACTUAL DATE text, SSV COMPANY text, SSV AGENT text, SSV BLOCK text,
      SSV DOC LINK text, SSV PLANNED DATE text, SSV REGISTRATION STATUS text, SSV STATUS text, SSV SYNDIC text, SSV SYNDIC MAIL text, SSV SYNDIC NAME text, SSV SYNDIC PHONE text, SSV TIMESTAMP text, TSA 1ST REMINDER DATE text, TSA 2ND REMINDER DATE text, TSA 3RD REMINDER DATE text, TSA 4TH REMINDER DATE text, TSA DOC FOR SIGNATURE text, TSA DOC SIGNED text, TSA COMPANY text, TSA GENERAL ASSEMBLY DATE text, TSA NEGOTIATOR text, TSA NEGOTIATOR COMMENTS text, TSA READY TO SEND DATE text, TSA REFUSED DATE text, TSA REGISTRATION STATUS text, TSA SENT DATE text, TSA SIGNED DATE text, TSA STATUS text, ACT HP CY text, ACT HP CY DEADLINE text, ACT SSV CY text, ACT SSV DEADLINE text, ACT UNIFIBER text,
      ACT UNIFIBER DATE text, APP CCP SSV SU COUNT text, APP CHK SU COUNT text, APP PROCESSED text, BLD ALL READY STATUS text, BLD COMPANY text, BLD FIBER BLOWN ACTUAL DATE text, BLD FIBER BLOWN PLANNED DATE text, BLD FIBER BLOWN STATUS text, BLD FIBER SPLICED ACTUAL DATE text, BLD FIBER SPLICED PLANNED DATE text, BLD FIBER SPLICED STATUS text, BLD INTRO ACTUAL DATE text, BLD INTRO PLANNED DATE text, BLD INTRO STATUS text, BLD SSV USABILITY text, BLD VC ACTUAL DATE text, BLD VC PLANNED DATE text, BLD VC STATUS text, CCP CHECK DONE text, CCP SSV BU COUNT text, CCP SSV LOW FLOOR text, CCP SSV LU COUNT text, CCP SSV QUADRANT text, CCP SSV TOTAL UNITS text, CCP SSV UPPER FLOOR text, CHK SSV BU COUNT text, CHK SSV DOC LINK text, CHK SSV LU COUNT text, CHK SSV QUADRANT text,
      CHK SSV TOTAL UNITS text, CHK SSV UPPER FLOOR text, CHK TSA DOC FOR SIGNATURE text, CHK TSA DOC SIGNED text, CHK TSA STATUS text, PST CENTRAL POP STATUS text, PST DEL STAT CODE DESC text, PST DEL HCA text, PST HP ACTUAL DATE text, PST HP PLANNED DATE text, SSV VALIDATOR text, STS ACTUAL DATE text, STS DOC LINK text, STS PARTNER text, STS PLANNED DATE text, STS QUADRANT text, STS STATUS text, STS UNITS COUNT text, CCP cleanup scope text, CCP CLEANUP COMMENT text, Audit report text, Audit report date text, PRIORITY text, SSV VALIDATION STATUS text, VALIDATION COMMENT SSV text, SSV validation date text, SSV validation counter text, Picture Quality text, Cable/material trajectory text, Quadrant Design text,
      Contact Details text, Building Group Check text, SSV BLDG GRP MAIN ADDRESS CHK text, DMP LOCATION CHK text, SSV SU COUNT CHK text, SSV BU COUNT CHK text, SSV LU COUNT CHK text, SSV TOTAL UNITS CHK text, TSA VALIDATION STATUS text, VALIDATION COMMENT TSA text, TSA validation date text, TSA validation counter text, REWORK STATUS SSV text, REWORK STATUS TSA text, REFUSAL RESPONSIBILITY SSV text, REFUSAL RESPONSIBILITY TSA text, REFUSAL REASON SSV text, REFUSAL REASON TSA text, ACTION REQUIRED FROM SSV text, ACTION REQUIRED FROM TSA text
    -> Remove_comments_about_duplicates
address_scoping (reader POSTGIS_1) [off]
    attributes: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
address (reader POSTGIS_1)
    attributes: id serial,BTree, area_id int4,BTree, surveyed_by_id int4,BTree, created_at timestamp, updated_at timestamp, jvid int4,BTree, jvid_use varchar(255), belmap_address_id int4,BTree, belmap_building_id int4,BTree, street_name text,BTree, house_number text,BTree, house_number_extension text,BTree, bus_number text,BTree, appartment_number text, postal_code text,BTree, municipality text, building_type varchar(255),BTree, city text,BTree, x float8, y float8, home_released bool, home_released_date timestamp, survey_status varchar(255), survey_date timestamp, status varchar(255),BTree, service_type text, address_source varchar(255),BTree, delivery_status int4, reason_not_homes_passed int4, dwelling_unit_type varchar(255),
      building_use text, lot text, distribution_point_number text, dependency_of_others int4, homes_passed_plan_date timestamp, homes_passed_actual_date timestamp, civil_plan_date timestamp, installation_type varchar(255), length_estimate_from_street int4, existing_duct_frontyard text, lat float8, lon float8, amount_of_meters_dug int4, cocon_frame text, quadrant text, deleted_at timestamp, street_survey_distribution_way varchar(255), homes_connect_at timestamp, internal_remarks text, action_needed bool, capakey text, nis5 int4, nis9 text, preferred_distribution text, hc_type text, hc_length int4, num_floor int4, area_pop_id int4,BTree, central_pop_id int4,BTree, scopelist_v0 date,
      scopelist_v15 date, scopelist_v2 date, first_hp_wip date, first_hp_hca date, sub_address_of int4,BTree, belmap_version int4,BTree, home_release_blocked_at timestamp, home_release_blocked_reason varchar(255), main_address bool, fiberzone text, house_entry_deploy_type varchar(255), approved_for_release bool, home_release_reverted_at timestamp, quadrant_pst text, out_of_scope_at timestamp, ftu_location text, mdu_ssv text, quote_approved bool, pst_update_blocked bool, home_release_blocked_by_delay_id int4,BTree, batch text, building_group text, type text, distance_source text, pst_update_blocked_reason text, amount_of_meters_aerial int4, amount_of_meters_facade int4, homes_passed_wip_actual_date timestamp, ftu_floor int4, ftu_location_other text,
      ftu_other_room bool, excavation_above int4, quote_reference text, quote_required text, asphalt bool, twin_jvid int4, sdu_exceptional bool, meters_public int8, meters_private int8, meters_indoor int8, meters_existing_drop int8, quote_cost int8, rsn_trench text
    -> AttributeCreator_2
area (reader POSTGIS_1) [off]
    attributes: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

Bookmark: Apply validation results to SSV - Consolidated SSV input
Remove_comments_about_duplicates: TestFilter
    DEFAULT_VALUE = <UNFILTERED>
    PASSED_TEST_GROUP_OUTPUT = FIRST
    TEST_LIST:
      "BOOL_OP,OR,COMPOSITE_TEST,""""""1 OR 2"""""",TEST_CLAUSE,CASE_INSENSITIVE_TEST @Value(VALIDATION COMMENT SSV) CONTAINS uplicat
      CASE_INSENSITIVE_TEST @Value(VALIDATION COMMENT SSV) CONTAINS oublo",Duplicate,"BOOL_OP,COMPOSITE,COMPOSITE_TEST,""""""1 AND ( 2 OR ( NOT 3 AND 4 ))"""""",TEST_CLAUSE,TEST @Value(SSV STATUS) = NOT EXISTING
      TEST @sum(@Value(SSV BU COUNT CHK),@Value(SSV LU COUNT CHK)) = 0
      TEST SSV BU COUNT CHK ATTRIBUTE_HAS_A_VALUE ""
      TEST SSV LU COUNT CHK NOT_ATTRIBUTE_HAS_A_VALUE """,NOT EXISTING
    NOT EXISTING -> Set_0_for_not_existing
    <UNFILTERED> -> Update_values_by_validated_data
Set_0_for_not_existing: AttributeManager
    ATTR_TABLE:
      SET_TO APP SSV BU COUNT (buffer) = FME_CONDITIONAL:DEFAULT_VALUE'_FME_NO_OP_'BOOL_OP;COMPOSITE;COMPOSITE_TEST;1 AND ( 2 OR ( NOT 3 AND 4 ));TEST @Value(SSV STATUS) = NOT EXISTING;TEST @sum(@Value(SSV BU COUNT CHK),@Value(SSV LU COUNT CHK)) = 0;TEST SSV BU COUNT CHK ATTRIBUTE_HAS_A_VALUE _FME_BLANK_STRING_;TEST SSV LU COUNT CHK NOT_ATTRIBUTE_HAS_A_VALUE _FME_BLANK_STRING_'0'FME_NUM_CONDITIONS2___
      SET_TO APP SSV LU COUNT (buffer) = FME_CONDITIONAL:DEFAULT_VALUE'_FME_NO_OP_'BOOL_OP;COMPOSITE;COMPOSITE_TEST;1 AND ( 2 OR ( NOT 3 AND 4 ));TEST @Value(SSV STATUS) = NOT EXISTING;TEST @sum(@Value(SSV BU COUNT CHK),@Value(SSV LU COUNT CHK)) = 0;TEST SSV BU COUNT CHK ATTRIBUTE_HAS_A_VALUE _FME_BLANK_STRING_;TEST SSV LU COUNT CHK NOT_ATTRIBUTE_HAS_A_VALUE _FME_BLANK_STRING_'0'FME_NUM_CONDITIONS2___
      SET_TO APP SSV TOTAL UNITS (buffer) = FME_CONDITIONAL:DEFAULT_VALUE'_FME_NO_OP_'BOOL_OP;COMPOSITE;COMPOSITE_TEST;1 AND ( 2 OR ( NOT 3 AND 4 ));TEST @Value(SSV STATUS) = NOT EXISTING;TEST @sum(@Value(SSV BU COUNT CHK),@Value(SSV LU COUNT CHK)) = 0;TEST SSV BU COUNT CHK ATTRIBUTE_HAS_A_VALUE _FME_BLANK_STRING_;TEST SSV LU COUNT CHK NOT_ATTRIBUTE_HAS_A_VALUE _FME_BLANK_STRING_'0'FME_NUM_CONDITIONS2___
    -> Update_values_by_validated_data
Update_values_by_validated_data: AttributeManager
    ATTR_TABLE:
      SET_TO APP SSV BLDG GRP MAIN ADDRESS (buffer) = FME_CONDITIONAL:DEFAULT_VALUE'_FME_NO_OP_'BOOL_OP;OR;COMPOSITE_TEST;1;TEST SSV BLDG GRP MAIN ADDRESS CHK ATTRIBUTE_HAS_A_VALUE _FME_BLANK_STRING_'@Value(SSV BLDG GRP MAIN ADDRESS CHK)'FME_NUM_CONDITIONS2___
      SET_TO APP SSV BU COUNT (buffer) = FME_CONDITIONAL:DEFAULT_VALUE'_FME_NO_OP_'BOOL_OP;OR;COMPOSITE_TEST;1;TEST SSV BU COUNT CHK ATTRIBUTE_HAS_A_VALUE _FME_BLANK_STRING_'@Value(SSV BU COUNT CHK)'FME_NUM_CONDITIONS2___
      SET_TO APP SSV LU COUNT (buffer) = FME_CONDITIONAL:DEFAULT_VALUE'_FME_NO_OP_'BOOL_OP;OR;COMPOSITE_TEST;1;TEST SSV LU COUNT CHK ATTRIBUTE_HAS_A_VALUE _FME_BLANK_STRING_'@Value(SSV LU COUNT CHK)'FME_NUM_CONDITIONS2___
      SET_TO APP SSV TOTAL UNITS (buffer) = FME_CONDITIONAL:DEFAULT_VALUE'_FME_NO_OP_'BOOL_OP;OR;COMPOSITE_TEST;1;TEST SSV TOTAL UNITS CHK ATTRIBUTE_HAS_A_VALUE _FME_BLANK_STRING_'@Value(SSV TOTAL UNITS CHK)'FME_NUM_CONDITIONS2___
    -> Sort_by_address_-_validation_status_-_total_LU
Sort_by_address_-_validation_status_-_total_LU: Sorter
    SORT_PARM = DMP POSTAL CODE NATURAL ASCENDING DMP STREET NATURAL ASCENDING DMP HOUSENUMBER NATURAL ASCENDING SSV VALIDATION STATUS NATURAL DESCENDING APP SSV TOTAL UNITS NATURAL DESCENDING
    SORTED -> Remove_duplicate_MDU
Remove_duplicate_MDU: DuplicateFilter
    INPUT_ORDERED_CHOICE_LOOKUP = YES
    KEYATTR = DMP HOUSENUMBER DMP POSTAL CODE DMP STREET
    INPUT_ORDERED_CHOICE = Yes
    UNIQUE -> AttributeRemover
AttributeRemover
    REMOVE_ATTRS = ACT HP CY,ACT HP CY DEADLINE,ACT SSV CY,ACT SSV DEADLINE,ACT UNIFIBER,ACT UNIFIBER DATE,APP CCP SSV SU COUNT,APP CHK SU COUNT,APP PROCESSED,Audit report,Audit report date,BLD ALL READY STATUS,BLD COMPANY,BLD FIBER BLOWN ACTUAL DATE,BLD FIBER BLOWN PLANNED DATE,BLD FIBER BLOWN STATUS,BLD FIBER SPLICED ACTUAL DATE,BLD FIBER SPLICED PLANNED DATE,BLD FIBER SPLICED STATUS,BLD INTRO ACTUAL DATE,BLD INTRO PLANNED DATE,BLD INTRO STATUS,BLD SSV USABILITY,BLD VC ACTUAL DATE,BLD VC PLANNED DATE,BLD VC STATUS,Building Group Check,Cable/material trajectory,CCP CHECK DONE,CCP CLEANUP COMMENT,CCP cleanup scope,CCP SSV BU COUNT,CCP SSV LOW FLOOR,CCP SSV LU COUNT,CCP SSV QUADRANT,CCP SSV TOTAL UNITS,CCP SSV UPPER FLOOR,CHK SSV BU COUNT,CHK SSV DOC LINK,CHK SSV LU COUNT,CHK SSV QUADRANT,CHK SSV TOTAL UNITS,CHK SSV UPPER FLOOR,CHK TSA DOC FOR SIGNATURE,CHK TSA DOC SIGNED,CHK TSA STATUS,Contact Details,item_id,Picture Quality,PRIORITY,PST CENTRAL POP STATUS,PST DEL HCA,PST DEL STAT CODE DESC,PST HP ACTUAL DATE,PST HP PLANNED DATE,Quadrant Design,SSV ACTUAL DATE,SSV AGENT,SSV BLDG GRP MAIN ADDRESS CHK,SSV BLOCK,SSV BU COUNT CHK,SSV DOC LINK,SSV LU COUNT CHK,SSV PLANNED DATE,SSV REGISTRATION STATUS,SSV SU COUNT CHK,SSV SYNDIC,SSV SYNDIC MAIL,SSV SYNDIC NAME,SSV SYNDIC PHONE,SSV TIMESTAMP,SSV TOTAL UNITS CHK,SSV validation counter,SSV validation date,SSV VALIDATION STATUS,SSV VALIDATOR,STS ACTUAL DATE,STS DOC LINK,STS PARTNER,STS PLANNED DATE,STS QUADRANT,STS STATUS,STS UNITS COUNT,TSA 1ST REMINDER DATE,TSA 2ND REMINDER DATE,TSA 3RD REMINDER DATE,TSA 4TH REMINDER DATE,TSA DOC FOR SIGNATURE,TSA DOC SIGNED,TSA GENERAL ASSEMBLY DATE,TSA NEGOTIATOR,TSA NEGOTIATOR COMMENTS,TSA READY TO SEND DATE,TSA REFUSED DATE,TSA REGISTRATION STATUS,TSA SENT DATE,TSA SIGNED DATE,TSA STATUS,TSA validation counter,TSA validation date,TSA VALIDATION STATUS,VALIDATION COMMENT SSV,VALIDATION COMMENT TSA
    -> Counter
Counter
    CNT_ATTR = MDU_ID
    DOMAIN = counter
    SCOPE = Global
    START = 1
    -> AttributeManager
AttributeManager
    ATTR_TABLE:
      SET_TO MDU_ID (int64) = MDU_@Value(MDU_ID)
      SET_TO MDU_Total (varchar(200)) = @sum(@Value(APP SSV BU COUNT),@Value(APP SSV LU COUNT))
    -> TestFilter

Bookmark: Define BG ID
TestFilter
    DEFAULT_VALUE = <UNFILTERED>
    PASSED_TEST_GROUP_OUTPUT = FIRST
    TEST_LIST = "BOOL_OP,OR,COMPOSITE_TEST,""""""1"""""",TEST_CLAUSE,TEST APP SSV BLDG GRP MAIN ADDRESS ATTRIBUTE_HAS_A_VALUE """,APP SSV BLDG GRP MAIN ADDRESS ATTRIBUTE_HAS_A_VALUE
    APP SSV BLDG GRP MAIN ADDRESS ATTRIBUTE_HAS_A_VALUE -> DuplicateFilter
    APP SSV BLDG GRP MAIN ADDRESS ATTRIBUTE_HAS_A_VALUE -> FeatureJoiner [LEFT]
    <UNFILTERED> -> FeatureJoiner_2 [RIGHT]
DuplicateFilter
    INPUT_ORDERED_CHOICE_LOOKUP = NO
    KEYATTR = APP SSV BLDG GRP MAIN ADDRESS
    INPUT_ORDERED_CHOICE = No
    UNIQUE -> Counter_2
Counter_2
    CNT_ATTR = BG_ID
    DOMAIN = counter
    SCOPE = Global
    START = 1
    -> AttributeManager_2
AttributeManager_2
    ATTR_TABLE:
      REMOVE task (buffer)
      REMOVE DMP AREA AREA ID (buffer)
      REMOVE DMP AREA NAME (buffer)
      REMOVE DMP POSTAL CODE (buffer)
      REMOVE DMP MUNICIPALITY (buffer)
      REMOVE DMP CITY (buffer)
      REMOVE DMP STREET (buffer)
      REMOVE DMP HOUSENUMBER (buffer)
      REMOVE DMP BUILDING KEY (buffer)
      REMOVE DMP BELMAP LU COUNT (buffer)
      REMOVE DMP POP AREA NAME (buffer)
      REMOVE DMP IN SCOPE (buffer)
      REMOVE APP SSV BLDG GRP INDIV TREATMENT (buffer)
      REMOVE APP SSV BU COUNT (buffer)
      REMOVE APP SSV BUILDING GROUP (buffer)
      REMOVE APP SSV BUILDING TYPE (buffer)
      REMOVE APP SSV DEPLOYMENT TYPE (buffer)
      REMOVE APP SSV LOW FLOOR (buffer)
      REMOVE APP SSV LU COUNT (buffer)
      REMOVE APP SSV QUADRANT (buffer)
      REMOVE APP SSV SU COUNT (buffer)
      REMOVE APP SSV TOTAL UNITS (buffer)
      REMOVE APP SSV UPPER FLOOR (buffer)
      REMOVE DMP LOCATION CHK (buffer)
      REMOVE Doubles (buffer)
      REMOVE SSV COMPANY (buffer)
      REMOVE TSA COMPANY (buffer)
      REMOVE REWORK STATUS SSV (buffer)
      REMOVE REWORK STATUS TSA (buffer)
      REMOVE REFUSAL RESPONSIBILITY SSV (buffer)
      REMOVE REFUSAL RESPONSIBILITY TSA (buffer)
      REMOVE REFUSAL REASON SSV (buffer)
      REMOVE REFUSAL REASON TSA (buffer)
      REMOVE ACTION REQUIRED FROM SSV (buffer)
      REMOVE ACTION REQUIRED FROM TSA (buffer)
      REMOVE SSV STATUS (buffer)
      SET_TO BG_ID (int64) = BG_@Value(BG_ID)
      REMOVE MDU_ID (int64)
    -> FeatureJoiner_2 [LEFT]
    -> FeatureJoiner [RIGHT]
    -> FeatureJoiner_5 [LEFT]
FeatureJoiner_2
    ATTR_CONFLICT_RES_LOOKUP = USE_LEFT
    GEOMETRY_HANDLING_LOOKUP = USE_LEFT
    JOIN_KEYS = APP SSV BLDG GRP MAIN ADDRESS task AUTO
    JOIN_MODE = Inner
    ATTR_CONFLICT_RES = Prefer Left
    GEOMETRY_HANDLING = Prefer Left
    JOINED -> DuplicateFilter_2
    UNJOINED_RIGHT -> DuplicateFilter_2
FeatureJoiner
    ATTR_CONFLICT_RES_LOOKUP = USE_LEFT
    GEOMETRY_HANDLING_LOOKUP = USE_LEFT
    JOIN_KEYS = APP SSV BLDG GRP MAIN ADDRESS APP SSV BLDG GRP MAIN ADDRESS AUTO
    JOIN_MODE = Inner
    ATTR_CONFLICT_RES = Prefer Left
    GEOMETRY_HANDLING = Prefer Left
    JOINED -> DuplicateFilter_2
    UNJOINED_RIGHT -> DuplicateFilter_2
DuplicateFilter_2
    INPUT_ORDERED_CHOICE_LOOKUP = NO
    KEYATTR = MDU_ID
    INPUT_ORDERED_CHOICE = No
    UNIQUE -> FeatureJoiner_5 [RIGHT]
    UNIQUE -> FeatureJoiner_6 [LEFT]
FeatureJoiner_5
    ATTR_CONFLICT_RES_LOOKUP = USE_LEFT
    GEOMETRY_HANDLING_LOOKUP = USE_LEFT
    JOIN_KEYS = APP SSV BLDG GRP MAIN ADDRESS task AUTO
    JOIN_MODE = Inner
    ATTR_CONFLICT_RES = Prefer Left
    GEOMETRY_HANDLING = Prefer Left
    JOINED -> AttributeManager_3
AttributeManager_3
    ATTR_TABLE = SET_TO BG_Total (varchar(200)) = @sum(@Value(APP SSV LU COUNT),@Value(APP SSV BU COUNT))
    -> AttributeRemover_2
AttributeRemover_2
    REMOVE_ATTRS = ACTION REQUIRED FROM SSV,ACTION REQUIRED FROM TSA,APP SSV BLDG GRP INDIV TREATMENT,APP SSV BLDG GRP MAIN ADDRESS,APP SSV BU COUNT,APP SSV BUILDING GROUP,APP SSV BUILDING TYPE,APP SSV DEPLOYMENT TYPE,APP SSV LOW FLOOR,APP SSV LU COUNT,APP SSV QUADRANT,APP SSV SU COUNT,APP SSV TOTAL UNITS,APP SSV UPPER FLOOR,DMP AREA AREA ID,DMP AREA NAME,DMP BELMAP LU COUNT,DMP BUILDING KEY,DMP CITY,DMP HOUSENUMBER,DMP IN SCOPE,DMP LOCATION CHK,DMP MUNICIPALITY,DMP POP AREA NAME,DMP POSTAL CODE,DMP STREET,Doubles,MDU_ID,MDU_Total,REFUSAL REASON SSV,REFUSAL REASON TSA,REFUSAL RESPONSIBILITY SSV,REFUSAL RESPONSIBILITY TSA,REWORK STATUS SSV,REWORK STATUS TSA,SSV COMPANY,SSV STATUS,task,TSA COMPANY
    -> FeatureJoiner_6 [RIGHT]
FeatureJoiner_6
    ATTR_CONFLICT_RES_LOOKUP = USE_LEFT
    GEOMETRY_HANDLING_LOOKUP = USE_LEFT
    JOIN_KEYS = BG_ID BG_ID AUTO
    JOIN_MODE = Inner
    ATTR_CONFLICT_RES = Prefer Left
    GEOMETRY_HANDLING = Prefer Left
    JOINED -> BulkAttributeRenamer
    UNJOINED_LEFT -> BulkAttributeRenamer
    <REJECTED> -> FeatureJoiner_6__Rejected_
    <REJECTED> -> BulkAttributeRenamer
FeatureJoiner_6__Rejected_: Inspector
BulkAttributeRenamer
    ATTRCHOICE_ACTION = SELECTED
    ATTRLIST = ACTION REQUIRED FROM SSV ACTION REQUIRED FROM TSA APP SSV BLDG GRP INDIV TREATMENT APP SSV BLDG GRP MAIN ADDRESS APP SSV BU COUNT APP SSV BUILDING GROUP APP SSV BUILDING TYPE APP SSV DEPLOYMENT TYPE APP SSV LOW FLOOR APP SSV LU COUNT APP SSV SU COUNT APP SSV TOTAL UNITS APP SSV UPPER FLOOR DMP AREA AREA ID DMP AREA NAME DMP BELMAP LU COUNT DMP BUILDING KEY DMP CITY DMP HOUSENUMBER DMP IN SCOPE DMP LOCATION CHK DMP MUNICIPALITY DMP POP AREA NAME DMP POSTAL CODE DMP STREET Doubles REFUSAL REASON SSV REFUSAL REASON TSA REFUSAL RESPONSIBILITY SSV REFUSAL RESPONSIBILITY TSA REWORK STATUS SSV REWORK STATUS TSA SSV COMPANY SSV STATUS task TSA COMPANY
    MODE_CHOICE = RENAME
    PATTERN_ACTION_DISP = ADDPREFIX
    REPLACE_STR = SSV_
    ATTRCHOICE = Selected Attributes
    -> FeatureJoiner_3 [RIGHT]
    -> FeatureJoiner_4 [RIGHT]

Bookmark: Apply MDU ID - BG ID to JVID and BL total
AttributeCreator_2
    ATTR_TABLE = SET_TO Depl_type (varchar(200)) = @Left(@Value(delivery_status),1)
    -> BL-DL
BL-DL: TestFilter
    DEFAULT_VALUE = <UNFILTERED>
    PASSED_TEST_GROUP_OUTPUT = FIRST
    TEST_LIST:
      "BOOL_OP,AND,COMPOSITE_TEST,""""""1 AND 2"""""",TEST_CLAUSE,TEST scopelist_v2 ATTRIBUTE_HAS_A_VALUE ""
      TEST scopelist_v15 ATTRIBUTE_VALUE_NULL """,BL,"BOOL_OP,AND,COMPOSITE_TEST,""""""1 AND 2"""""",TEST_CLAUSE,TEST scopelist_v2 ATTRIBUTE_HAS_A_VALUE ""
      TEST scopelist_v15 ATTRIBUTE_HAS_A_VALUE """,BL-DL,"BOOL_OP,AND,COMPOSITE_TEST,""""""1 AND 2"""""",TEST_CLAUSE,TEST scopelist_v2 ATTRIBUTE_VALUE_NULL ""
      TEST scopelist_v15 ATTRIBUTE_HAS_A_VALUE """,DL,"BOOL_OP,AND,COMPOSITE_TEST,""""""1 AND 2"""""",TEST_CLAUSE,TEST scopelist_v2 ATTRIBUTE_VALUE_NULL ""
      TEST scopelist_v15 ATTRIBUTE_VALUE_NULL """,Out of scope
    BL -> FeatureJoiner_3 [LEFT]
    BL-DL -> FeatureJoiner_3 [LEFT]
FeatureJoiner_3
    ATTR_CONFLICT_RES_LOOKUP = USE_LEFT
    GEOMETRY_HANDLING_LOOKUP = USE_LEFT
    JOIN_KEYS = street_name SSV_DMP STREET AUTO house_number_extension SSV_DMP HOUSENUMBER AUTO postal_code SSV_DMP POSTAL CODE AUTO
    JOIN_MODE = Inner
    ATTR_CONFLICT_RES = Prefer Left
    GEOMETRY_HANDLING = Prefer Left
    JOINED -> BulkAttributeRemover
    UNJOINED_LEFT -> FeatureJoiner_4 [LEFT]
BulkAttributeRemover
    ATTR_EXP = SSV_
    -> StatisticsCalculator
StatisticsCalculator
    ATTR_ACCUM_MODE = None
    CALCULATION_MODE = NUMERIC
    FEAT_STATS = jvid,NUMERIC_MODE,,,COUNT,,,,,,,,,,
    GROUP_BY = MDU_ID
    COMPLETE -> AttributeRenamer
AttributeRenamer
    ATTR_TABLE = RENAME_SET_DEFAULT jvid.total_count > BL_MDU_Total
    KEEP_RENAMED_ONLY = no
    MISSING_INPUT_ATTRS = REMOVE
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST BG_ID ATTRIBUTE_HAS_A_VALUE """,BG_ID ATTRIBUTE_HAS_A_VALUE
    BG_ID ATTRIBUTE_HAS_A_VALUE -> TestFilter_3
    <UNFILTERED> -> FeatureJoiner_4 [LEFT]
FeatureJoiner_4
    ATTR_CONFLICT_RES_LOOKUP = USE_LEFT
    GEOMETRY_HANDLING_LOOKUP = USE_LEFT
    JOIN_KEYS = building_group SSV_task AUTO
    JOIN_MODE = Inner
    ATTR_CONFLICT_RES = Prefer Left
    GEOMETRY_HANDLING = Prefer Left
    JOINED -> BulkAttributeRemover_2
    UNJOINED_LEFT -> DuplicateFilter_3
    <REJECTED> -> FeatureJoiner_4__Rejected_
    <REJECTED> -> BulkAttributeRemover_3
BulkAttributeRemover_2
    ATTR_EXP = SSV_
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST BG_ID ATTRIBUTE_HAS_A_VALUE """,BG_ID ATTRIBUTE_HAS_A_VALUE
    BG_ID ATTRIBUTE_HAS_A_VALUE -> StatisticsCalculator_2
    <UNFILTERED> -> DuplicateFilter_3
StatisticsCalculator_2
    ATTR_ACCUM_MODE = None
    CALCULATION_MODE = NUMERIC
    FEAT_STATS = jvid,NUMERIC_MODE,,,COUNT,,,,,,,,,,
    GROUP_BY = BG_ID
    COMPLETE -> AttributeRenamer_2
AttributeRenamer_2
    ATTR_TABLE = RENAME_SET_DEFAULT jvid.total_count > BL_BG_Total
    KEEP_RENAMED_ONLY = no
    MISSING_INPUT_ATTRS = REMOVE
    -> DuplicateFilter_3
BulkAttributeRemover_3
    ATTR_EXP = SSV_
    -> DuplicateFilter_3
DuplicateFilter_3
    INPUT_ORDERED_CHOICE_LOOKUP = NO
    KEYATTR = jvid
    INPUT_ORDERED_CHOICE = No
    UNIQUE -> AttributeCreator
AttributeCreator
    ATTR_TABLE = SET_TO Delta (varchar(200)) = FME_CONDITIONAL:DEFAULT_VALUE'_FME_NO_OP_'BOOL_OP;OR;COMPOSITE_TEST;1;TEST BG_ID ATTRIBUTE_HAS_A_VALUE _FME_BLANK_STRING_'@sub(@Value(BG_Total),@Value(BL_BG_Total))'BOOL_OP;OR;COMPOSITE_TEST;1;TEST MDU_ID ATTRIBUTE_HAS_A_VALUE _FME_BLANK_STRING_'@sub(@Value(MDU_Total),@Value(BL_MDU_Total))'FME_NUM_CONDITIONS3___
    -> TestFilter_4
    -> TestFilter_6
FeatureJoiner_4__Rejected_: Inspector

Bookmark: Feedback file
TestFilter_6
    DEFAULT_VALUE = <UNFILTERED>
    PASSED_TEST_GROUP_OUTPUT = FIRST
    TEST_LIST:
      "BOOL_OP,OR,COMPOSITE_TEST,""""""1 OR 2"""""",TEST_CLAUSE,TEST @Value(Delta) = 0
      TEST Delta ATTRIBUTE_VALUE_NULL """,Delta =0,"BOOL_OP,OR,COMPOSITE_TEST,""""""1"""""",TEST_CLAUSE,TEST BG_ID ATTRIBUTE_HAS_A_VALUE """,BG ID
    BG ID -> Aggregator
    <UNFILTERED> -> TestFilter_7
Aggregator
    ACCUM_ATTRS_NAME = Drop Incoming Attributes
    AGGREGATE_TYPE = Homogeneous Collection (If Possible)
    CONCAT_ATTRS = delivery_status bus_number jvid
    GROUP_BY = BG_ID Delta BG_Total BL_BG_Total
    MODE = Geometry - Assemble One Level
    SEP = ,
TestFilter_7
    DEFAULT_VALUE = <UNFILTERED>
    PASSED_TEST_GROUP_OUTPUT = FIRST
    TEST_LIST = "BOOL_OP,OR,COMPOSITE_TEST,""""""1"""""",TEST_CLAUSE,TEST MDU_ID ATTRIBUTE_HAS_A_VALUE """,MDU ID
    MDU ID -> Aggregator_2
Aggregator_2
    ACCUM_ATTRS_NAME = Drop Incoming Attributes
    AGGREGATE_TYPE = Homogeneous Collection (If Possible)
    CONCAT_ATTRS = delivery_status bus_number jvid
    GROUP_BY = MDU_ID Delta BL_MDU_Total MDU_Total
    MODE = Geometry - Assemble One Level
    SEP = ,

Bookmark: Stats
TestFilter_4
    DEFAULT_VALUE = <UNFILTERED>
    PASSED_TEST_GROUP_OUTPUT = FIRST
    TEST_LIST = "BOOL_OP,OR,COMPOSITE_TEST,""""""1"""""",TEST_CLAUSE,TEST BG_ID ATTRIBUTE_HAS_A_VALUE """,BG ID
    <UNFILTERED> -> TestFilter_5
    BG ID -> DuplicateFilter_4
DuplicateFilter_4
    INPUT_ORDERED_CHOICE_LOOKUP = NO
    KEYATTR = BG_ID
    INPUT_ORDERED_CHOICE = No
    UNIQUE -> TestFilter_5
TestFilter_5
    DEFAULT_VALUE = <UNFILTERED>
    PASSED_TEST_GROUP_OUTPUT = FIRST
    TEST_LIST = "BOOL_OP,OR,COMPOSITE_TEST,""""""1"""""",TEST_CLAUSE,TEST MDU_ID ATTRIBUTE_HAS_A_VALUE """,MDU ID
    MDU ID -> DuplicateFilter_5
    <UNFILTERED> -> StatisticsCalculator_3
DuplicateFilter_5
    INPUT_ORDERED_CHOICE_LOOKUP = NO
    KEYATTR = MDU_ID
    INPUT_ORDERED_CHOICE = No
    UNIQUE -> StatisticsCalculator_3
    UNIQUE -> AttributeCreator_3
StatisticsCalculator_3
    ATTR_ACCUM_MODE = None
    CALCULATION_MODE = NUMERIC
    FEAT_STATS = Delta,NUMERIC_MODE,,,,SUM,,,,,,,,,
